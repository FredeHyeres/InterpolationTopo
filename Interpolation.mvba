Attribute VB_Name = "CAltitudeSelection"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CAltitudeSelection - Resultat d'une recherche d'altitude
'
' Memorise la valeur altitude trouvee, son origine dans le repere du modele
' actif, l'element source eventuel, et indique si la source vient d'une
' reference attachee. Compatible VBA 6.x : pas de membre Public de type Point3d.
'==============================================================================
Option Explicit

Public ValeurTexte      As String
Public TagDefName       As String
Public EstReference     As Boolean

Public oTexte           As TextElement
Public oTag             As TagElement
Public oCellule         As CellElement
Public oAttachment      As Object

Private m_dX            As Double
Private m_dY            As Double
Private m_dZ            As Double

'------------------------------------------------------------------------------
Sub Vider()
    ValeurTexte = ""
    TagDefName = ""
    EstReference = False
    Set oTexte = Nothing
    Set oTag = Nothing
    Set oCellule = Nothing
    Set oAttachment = Nothing
    m_dX = 0#: m_dY = 0#: m_dZ = 0#
End Sub

'------------------------------------------------------------------------------
Sub DefinirOrigine(oPt As Point3d)
    m_dX = oPt.X
    m_dY = oPt.Y
    m_dZ = oPt.Z
End Sub

'------------------------------------------------------------------------------
Sub CopierOrigine(oPt As Point3d)
    oPt.X = m_dX
    oPt.Y = m_dY
    oPt.Z = m_dZ
End Sub

'------------------------------------------------------------------------------
Sub CopierDepuis(oSrc As CAltitudeSelection)
    If oSrc Is Nothing Then
        Vider
        Exit Sub
    End If

    ValeurTexte = oSrc.ValeurTexte
    TagDefName = oSrc.TagDefName
    EstReference = oSrc.EstReference
    Set oTexte = oSrc.oTexte
    Set oTag = oSrc.oTag
    Set oCellule = oSrc.oCellule
    Set oAttachment = oSrc.oAttachment

    Dim oPt As Point3d
    oSrc.CopierOrigine oPt
    DefinirOrigine oPt
End Sub

'------------------------------------------------------------------------------
Property Get Trouvee() As Boolean
    Trouvee = (Len(ValeurTexte) > 0)
End Property

Attribute VB_Name = "CBoiteEPInfo"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CBoiteEPInfo - Resultat du parsing d'une cellule regard/grille (BoiteEP)
'
' Contient les trois altitudes attendues :
'   T:    altitude du tampon         -> ZTampon      (flag TrouveTampon)
'   Fe:   altitude du fil d'eau      -> ZFilEau      (flag TrouveFilEau)
'   Prof: profondeur du regard       -> Profondeur   (flag TrouveProfondeur)
'
' Et l'element source + son origine dans le repere du modele actif.
' Compatible VBA 6.x : pas de membre Public de type Point3d (stocke en 3 Double).
'==============================================================================
Option Explicit

Public TrouveTampon         As Boolean
Public ZTampon              As Double

Public TrouveFilEau         As Boolean
Public ZFilEau              As Double

Public TrouveProfondeur     As Boolean
Public Profondeur           As Double

Public oCellule             As CellElement
Public NomCellule           As String
Public EstReference         As Boolean       ' True si la cellule vient d'un fichier attache
Public oAttachment          As Object        ' Attachment source (Nothing si modele actif)

Private m_dX                As Double
Private m_dY                As Double
Private m_dZ                As Double

'------------------------------------------------------------------------------
Sub Vider()
    TrouveTampon = False:      ZTampon = 0#
    TrouveFilEau = False:      ZFilEau = 0#
    TrouveProfondeur = False:  Profondeur = 0#
    Set oCellule = Nothing
    NomCellule = ""
    EstReference = False
    Set oAttachment = Nothing
    m_dX = 0#: m_dY = 0#: m_dZ = 0#
End Sub

'------------------------------------------------------------------------------
' On considere l'info valide si au moins le fil d'eau a ete trouve : c'est
' l'altitude utilisee pour le calcul de pente.
Property Get Valide() As Boolean
    Valide = TrouveFilEau
End Property

'------------------------------------------------------------------------------
Sub DefinirOrigine(oPt As Point3d)
    m_dX = oPt.X: m_dY = oPt.Y: m_dZ = oPt.Z
End Sub

Sub CopierOrigine(oPt As Point3d)
    oPt.X = m_dX: oPt.Y = m_dY: oPt.Z = m_dZ
End Sub

Property Get X() As Double: X = m_dX: End Property
Property Get Y() As Double: Y = m_dY: End Property
Property Get Z() As Double: Z = m_dZ: End Property

'------------------------------------------------------------------------------
Sub CopierDepuis(oSrc As CBoiteEPInfo)
    If oSrc Is Nothing Then Vider: Exit Sub
    TrouveTampon = oSrc.TrouveTampon:         ZTampon = oSrc.ZTampon
    TrouveFilEau = oSrc.TrouveFilEau:         ZFilEau = oSrc.ZFilEau
    TrouveProfondeur = oSrc.TrouveProfondeur: Profondeur = oSrc.Profondeur
    Set oCellule = oSrc.oCellule
    NomCellule = oSrc.NomCellule
    EstReference = oSrc.EstReference
    Set oAttachment = oSrc.oAttachment
    Dim oPt As Point3d
    oSrc.CopierOrigine oPt
    DefinirOrigine oPt
End Sub

Attribute VB_Name = "CBoiteEPParser"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CBoiteEPParser - Extrait T: / Fe: / Prof: d'une cellule regard/grille
'
' Structure attendue (validee via DebugBoiteEP.bas sur cellule "Boite EU") :
'   CellHeader
'     Shape / Shape / ...
'     TextNode              <- les textes sont sous un TextNode
'       Text "T: 91.98"
'       Text "Fe:90.86"
'       Text "Prof:1.12"
'
' Peut aussi lire des tags si le futur DGN les utilise a la place des textes.
' Robustesse : espaces libres apres le prefixe, separateur decimal , ou .
'==============================================================================
Option Explicit

'------------------------------------------------------------------------------
' Point d'entree unique : lit une cellule et retourne CBoiteEPInfo peuple.
' oElem peut etre un CellHeader ; toute autre chose renvoie un info vide.
Function Lire(oElem As Element) As CBoiteEPInfo
    Dim oInfo As New CBoiteEPInfo
    oInfo.Vider

    If oElem Is Nothing Then Set Lire = oInfo: Exit Function
    If oElem.Type <> msdElementTypeCellHeader Then Set Lire = oInfo: Exit Function

    Dim oCell As CellElement
    Set oCell = oElem
    Set oInfo.oCellule = oCell
    oInfo.NomCellule = oCell.Name
    oInfo.DefinirOrigine oCell.Origin

    ParcourirEnfants oCell.GetSubElements, oInfo

    Set Lire = oInfo
End Function

'------------------------------------------------------------------------------
' Parcours recursif : descend dans les sous-cellules et les text nodes,
' extrait chaque texte/tag rencontre pour tenter d'y lire T:/Fe:/Prof:.
Private Sub ParcourirEnfants(oEnum As ElementEnumerator, oInfo As CBoiteEPInfo)
    Do While oEnum.MoveNext
        Dim oElem As Element
        Set oElem = oEnum.Current

        If oElem.IsTextElement Then
            AnalyserChaine oElem.AsTextElement.Text, oInfo
        ElseIf oElem.Type = msdElementTypeTag Then
            AnalyserChaine CStr(oElem.AsTagElement.Value), oInfo
        ElseIf oElem.Type = msdElementTypeTextNode Then
            ParcourirEnfants oElem.AsTextNodeElement.GetSubElements, oInfo
        ElseIf oElem.Type = msdElementTypeCellHeader Then
            Dim oSub As CellElement
            Set oSub = oElem
            ParcourirEnfants oSub.GetSubElements, oInfo
        End If
    Loop
End Sub

'------------------------------------------------------------------------------
' Reconnait "T:...", "Fe:...", "Prof:..." (insensible a la casse, espaces libres).
' Met a jour les champs correspondants dans oInfo.
Private Sub AnalyserChaine(ByVal sTxt As String, oInfo As CBoiteEPInfo)
    Dim s As String
    s = Trim$(sTxt)
    If Len(s) = 0 Then Exit Sub

    Dim sLow As String
    sLow = LCase$(s)

    Dim dVal As Double

    If EstPrefixe(sLow, "prof") Then
        If ExtraireNombreApres(s, "prof", dVal) Then
            oInfo.Profondeur = dVal
            oInfo.TrouveProfondeur = True
        End If
        Exit Sub
    End If

    If EstPrefixe(sLow, "fe") Then
        If ExtraireNombreApres(s, "fe", dVal) Then
            oInfo.ZFilEau = dVal
            oInfo.TrouveFilEau = True
        End If
        Exit Sub
    End If

    If EstPrefixe(sLow, "t") Then
        If ExtraireNombreApres(s, "t", dVal) Then
            oInfo.ZTampon = dVal
            oInfo.TrouveTampon = True
        End If
        Exit Sub
    End If
End Sub

'------------------------------------------------------------------------------
' Vrai si sLow commence par sPref (deja en minuscule) suivi de : ou espace ou =
Private Function EstPrefixe(ByVal sLow As String, ByVal sPref As String) As Boolean
    EstPrefixe = False
    If Len(sLow) < Len(sPref) + 1 Then Exit Function
    If Left$(sLow, Len(sPref)) <> sPref Then Exit Function
    Dim c As String
    c = Mid$(sLow, Len(sPref) + 1, 1)
    EstPrefixe = (c = ":" Or c = " " Or c = "=")
End Function

'------------------------------------------------------------------------------
' Extrait le nombre situe apres le prefixe (et son separateur : / = / espaces).
' Accepte "." ou "," comme separateur decimal.
Private Function ExtraireNombreApres(ByVal sTxt As String, _
                                     ByVal sPref As String, _
                                     dOut As Double) As Boolean
    ExtraireNombreApres = False
    dOut = 0#

    Dim sReste As String
    sReste = Mid$(sTxt, Len(sPref) + 1)

    ' Retirer les separateurs de tete : ':', '=', espaces
    Do While Len(sReste) > 0
        Dim c As String
        c = Left$(sReste, 1)
        If c = ":" Or c = "=" Or c = " " Or c = vbTab Then
            sReste = Mid$(sReste, 2)
        Else
            Exit Do
        End If
    Loop

    ' Extraire le token nombre (chiffres + . / , + signe eventuel en tete)
    Dim sNb As String
    sNb = ""
    Dim i As Integer
    Dim bDot As Boolean: bDot = False
    For i = 1 To Len(sReste)
        Dim ch As String
        ch = Mid$(sReste, i, 1)
        If i = 1 And (ch = "+" Or ch = "-") Then
            sNb = sNb & ch
        ElseIf ch >= "0" And ch <= "9" Then
            sNb = sNb & ch
        ElseIf (ch = "." Or ch = ",") And Not bDot Then
            sNb = sNb & "."
            bDot = True
        Else
            Exit For
        End If
    Next i

    If Len(sNb) = 0 Then Exit Function
    If sNb = "+" Or sNb = "-" Or sNb = "." Then Exit Function

    dOut = Val(sNb)
    ExtraireNombreApres = True
End Function

Attribute VB_Name = "CInterpolation"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CInterpolation - Moteur de calcul pur
'
' Responsabilites :
'   - parsing d'un texte altitude (numerique, separateur, decimales)
'   - projection orthogonale d'un point sur une droite
'   - interpolation d'altitude par abscisse parametrique
'   - calcul geometrique : distance 2D, pente, gisement
'   - formatage d'une altitude
'
' Cette classe ne connait pas : symbologie, niveaux, couleurs, elements MST,
' formulaire, parametres de commande. Elle ne manipule que des donnees.
'==============================================================================
Option Explicit

Private Const PI As Double = 3.14159265358979

'==============================================================================
' Parsing
'==============================================================================

'------------------------------------------------------------------------------
' Vrai si s est un nombre au format normalise [+-]chiffres[.chiffres]
Function EstNombre(ByVal s As String) As Boolean
    EstNombre = False
    If Len(s) = 0 Then Exit Function
    If Left$(s, 1) = "+" Or Left$(s, 1) = "-" Then s = Mid$(s, 2)
    Dim i As Integer, nDots As Integer, nDigits As Integer, c As String
    For i = 1 To Len(s)
        c = Mid$(s, i, 1)
        If c = "." Then
            nDots = nDots + 1
            If nDots > 1 Then Exit Function
        ElseIf c >= "0" And c <= "9" Then
            nDigits = nDigits + 1
        Else
            Exit Function
        End If
    Next
    EstNombre = (nDigits > 0)
End Function

'------------------------------------------------------------------------------
' Lit l'altitude de la selection courante et charge le CPointRef.
' Renseigne aussi sSep ("." ou ",") et nDec (nb de decimales).
' Retourne False si le texte n'est pas numerique.
Function LireAltitudeTexte(oPoint As CPointRef, _
                            sSep As String, nDec As Integer) As Boolean
    LireAltitudeTexte = False
    oPoint.Invalider

    Dim sBrut As String
    sBrut = g_oSelectionCourante.ValeurTexte
    If InStr(sBrut, ",") > 0 Then
        sSep = ","
        sBrut = Replace(sBrut, ",", ".")
    Else
        sSep = "."
    End If

    If Not EstNombre(sBrut) Then Exit Function

    oPoint.Altitude = Val(sBrut)
    Dim ptOrigine As Point3d
    g_oSelectionCourante.CopierOrigine ptOrigine
    oPoint.DefinirPosition ptOrigine
    oPoint.Valide = True

    Dim nDot As Integer
    nDot = InStrRev(sBrut, ".")
    If nDot > 0 Then nDec = Len(sBrut) - nDot Else nDec = 0

    LireAltitudeTexte = True
End Function

'==============================================================================
' Geometrie
'==============================================================================

'------------------------------------------------------------------------------
Function Dist2D(oA As Point3d, oB As Point3d) As Double
    Dist2D = Sqr((oB.X - oA.X) ^ 2 + (oB.Y - oA.Y) ^ 2)
End Function

'------------------------------------------------------------------------------
' Variante pour deux points de reference (evite de manipuler des Point3d)
Function Dist2DRef(oP1 As CPointRef, oP2 As CPointRef) As Double
    Dist2DRef = Sqr((oP2.X - oP1.X) ^ 2 + (oP2.Y - oP1.Y) ^ 2)
End Function

'------------------------------------------------------------------------------
' Projette oC sur la droite oA-oB en plan.
' dT : abscisse parametrique (0=A, 1=B, negatif ou >1 = extrapolation)
' oRes : point projete avec Z interpole entre oA.Z et oB.Z
Sub ProjecterSurDroite(oA As Point3d, oB As Point3d, oC As Point3d, _
                       dT As Double, oRes As Point3d)
    Dim dX As Double, dY As Double, dL2 As Double
    dX = oB.X - oA.X: dY = oB.Y - oA.Y
    dL2 = dX * dX + dY * dY
    If dL2 < 0.0000000001 Then
        dT = 0: oRes = oA: Exit Sub
    End If
    dT = ((oC.X - oA.X) * dX + (oC.Y - oA.Y) * dY) / dL2
    oRes.X = oA.X + dT * dX
    oRes.Y = oA.Y + dT * dY
    oRes.Z = oA.Z + dT * (oB.Z - oA.Z)
End Sub

'------------------------------------------------------------------------------
' Variante : projette oC sur la droite definie par deux points de reference.
' Les classes de commande passent directement g_oP1/g_oP2.
Sub ProjecterSurSegment(oP1 As CPointRef, oP2 As CPointRef, oC As Point3d, _
                        dT As Double, oRes As Point3d)
    Dim oA As Point3d, oB As Point3d
    oP1.CopierPosition oA
    oP2.CopierPosition oB
    oA.Z = oP1.Altitude
    oB.Z = oP2.Altitude
    ProjecterSurDroite oA, oB, oC, dT, oRes
End Sub

'------------------------------------------------------------------------------
Function InterpolerZ(dZ1 As Double, dZ2 As Double, dT As Double) As Double
    InterpolerZ = dZ1 + (dZ2 - dZ1) * dT
End Function

'==============================================================================
' Indicateurs geometriques du segment P1-P2
'==============================================================================

'------------------------------------------------------------------------------
Function PentePct(oP1 As CPointRef, oP2 As CPointRef) As Double
    Dim dL As Double
    dL = Dist2DRef(oP1, oP2)
    If dL < 0.0000000001 Then PentePct = 0 Else _
        PentePct = (oP2.Altitude - oP1.Altitude) / dL * 100#
End Function

'------------------------------------------------------------------------------
Function GisementGon(oP1 As CPointRef, oP2 As CPointRef) As Double
    Dim dX As Double, dY As Double, dA As Double
    dX = oP2.X - oP1.X
    dY = oP2.Y - oP1.Y
    If Abs(dX) < 0.0000000001 And Abs(dY) < 0.0000000001 Then Exit Function
    dA = Atn2Priv(dX, dY)
    GisementGon = dA * 200# / PI
    If GisementGon < 0 Then GisementGon = GisementGon + 400#
End Function

Private Function Atn2Priv(ByVal dY As Double, ByVal dX As Double) As Double
    If dX > 0 Then
        Atn2Priv = Atn(dY / dX)
    ElseIf dX < 0 Then
        Atn2Priv = Atn(dY / dX) + IIf(dY >= 0, PI, -PI)
    Else
        Atn2Priv = IIf(dY >= 0, PI / 2#, -PI / 2#)
    End If
End Function

'------------------------------------------------------------------------------
Function InfoSegment(oP1 As CPointRef, oP2 As CPointRef) As String
    InfoSegment = "Pente=" & Format$(PentePct(oP1, oP2), "0.0") & "%" & _
                  "  Gisement=" & Format$(GisementGon(oP1, oP2), "0.00") & " gon"
End Function

'==============================================================================
' Angles
'==============================================================================

'------------------------------------------------------------------------------
' Angle en radians depuis l'axe X (sens trigonometrique) pour un vecteur (dDX, dDY).
Function Angle2D(dDX As Double, dDY As Double) As Double
    If Abs(dDX) < 0.0000000001 And Abs(dDY) < 0.0000000001 Then
        Angle2D = 0#
        Exit Function
    End If
    Angle2D = Atn2Priv(dDY, dDX)
End Function

'==============================================================================
' Formatage
'==============================================================================

'------------------------------------------------------------------------------
Function FormatAltitude(DZ As Double, nDec As Integer, sSep As String) As String
    Dim sFmt As String
    If nDec <= 0 Then sFmt = "0" Else sFmt = "0." & String$(nDec, "0")
    Dim sRes As String
    sRes = Format$(DZ, sFmt)
    ' Format$ suit la locale Windows : on normalise puis on applique le separateur source
    sRes = Replace(sRes, ",", ".")
    If sSep = "," Then sRes = Replace(sRes, ".", ",")
    FormatAltitude = sRes
End Function

'------------------------------------------------------------------------------
' Formate une pente en pourcentage en valeur absolue (la fleche indique le sens).
' nDec facultatif : nombre de decimales, defaut 1.
Function FormatPente(dPente As Double, sSep As String, _
                     Optional nDec As Integer = 1) As String
    Dim sFmt As String
    If nDec <= 0 Then sFmt = "0" Else sFmt = "0." & String$(nDec, "0")
    Dim sRes As String
    sRes = Format$(Abs(dPente), sFmt)
    sRes = Replace(sRes, ",", ".")
    If sSep = "," Then sRes = Replace(sRes, ".", ",")
    FormatPente = sRes & "%"
End Function

Attribute VB_Name = "CMoteurGraphique"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CMoteurGraphique - Creation des elements MicroStation
'
' Responsabilites :
'   - creer le texte altitude et le cercle pour un point topo valide
'   - dessiner l'apercu dynamique (Redraw) pendant le deplacement curseur
'
' Recoit un resultat deja calcule (point projete + altitude) et des parametres
' de symbologie (CMstSettings). Ne realise aucun calcul.
'==============================================================================
Option Explicit

'==============================================================================
' Creation definitive
'==============================================================================

'------------------------------------------------------------------------------
' Cree le texte altitude et le cercle au point projete, et les ajoute au modele.
Sub CreerPointTopo(oProj As Point3d, dZInterp As Double, oSettings As CMstSettings, _
                   oCalc As CInterpolation)
    Dim sAlt As String
    sAlt = oCalc.FormatAltitude(dZInterp, oSettings.oTexte.Decimales, _
                                oSettings.oTexte.SepDecimal)

    Dim oSrc As CAltitudeSelection
    Set oSrc = g_oSelectionP1

    If oSrc Is Nothing Then
        CreerTexteEtCercle oProj, sAlt, oSettings, oCalc
        Exit Sub
    End If

    If oSrc.EstReference Then
        ' On lit les references, mais on cree toujours dans le fichier actif.
        ' Cloner cellule/tag depuis une reference V8i est fragile : fallback sur
        ' texte + cercle, en gardant le format/symbologie de P1 si disponible.
        CreerTexteEtCercle oProj, sAlt, oSettings, oCalc

    ElseIf Not oSrc.oCellule Is Nothing Then
        ' --- Cas cellule : cloner, deplacer, modifier le texte interne ---
        ClonerCellule oSrc, oProj, sAlt, oCalc

    ElseIf Not oSrc.oTag Is Nothing Then
        ' --- Cas tag : cloner l'hote et reassocier un tag ---
        ClonerTag oSrc, oProj, sAlt, oSettings, oCalc

    Else
        ' --- Cas texte classique : texte + cercle ---
        CreerTexteEtCercle oProj, sAlt, oSettings, oCalc
    End If
End Sub

'------------------------------------------------------------------------------
' Cree uniquement le cercle au point projete.
Sub CreerCercleSeul(oProj As Point3d, oSettings As CMstSettings)
    Dim oCercle As EllipseElement
    Set oCercle = CreateEllipseElement2(Nothing, oProj, _
                      oSettings.oCercle.Rayon, oSettings.oCercle.Rayon, Matrix3dIdentity())
    oCercle.Color = oSettings.oCercle.Couleur
    Set oCercle.Level = ResolverNiveau(oSettings.oCercle.NomNiveau, oSettings)
    ActiveModelReference.AddElement oCercle
End Sub

'------------------------------------------------------------------------------
' Cree uniquement le texte altitude a la position choisie par l'utilisateur.
Sub CreerTexteSeul(oPtTexte As Point3d, DZ As Double, _
                   oSettings As CMstSettings, oCalc As CInterpolation)
    Dim sAlt As String
    sAlt = oCalc.FormatAltitude(DZ, oSettings.oTexte.Decimales, oSettings.oTexte.SepDecimal)

    Dim oRot As Matrix3d
    oRot = Matrix3dIdentity()
    On Error Resume Next
    If Not oSettings.oTextModele Is Nothing Then oRot = oSettings.oTextModele.Rotation
    On Error GoTo 0

    Dim oTxt As TextElement
    Dim bSansModele As Boolean
    On Error Resume Next
    Set oTxt = CreateTextElement1(oSettings.oTextModele, sAlt, oPtTexte, oRot)
    If oTxt Is Nothing Then
        Err.Clear
        bSansModele = True
        Set oTxt = CreateTextElement1(Nothing, sAlt, oPtTexte, oRot)
    End If
    On Error GoTo 0
    If bSansModele Or oSettings.oTextModele Is Nothing Or Not oSettings.oTexte.CommeModele Then
        oTxt.Color = oSettings.oTexte.Couleur
        Set oTxt.Level = ResolverNiveau(oSettings.oTexte.NomNiveau, oSettings)
    Else
        On Error Resume Next
        Dim sStyleNom As String
        sStyleNom = oSettings.oTextModele.TextStyle.Name
        If Err.Number = 0 And Len(sStyleNom) > 0 Then
            Dim oStyleLocal As TextStyle
            Set oStyleLocal = ActiveDesignFile.TextStyles(sStyleNom)
            If Not oStyleLocal Is Nothing Then
                oTxt.TextStyle = oStyleLocal
            End If
        End If
        Err.Clear
        Set oTxt.Level = ResolverNiveau(oSettings.oTexte.NomNiveau, oSettings)
        Err.Clear
        On Error GoTo 0
    End If
    ActiveModelReference.AddElement oTxt
End Sub

'------------------------------------------------------------------------------
' Apercu dynamique du texte altitude en placement libre (etape 3).
Sub DessinTexteLibre(ByVal DrawMode As MsdDrawingMode, _
                     oPtTexte As Point3d, DZ As Double, _
                     oSettings As CMstSettings, oCalc As CInterpolation)
    Dim sAlt As String
    sAlt = oCalc.FormatAltitude(DZ, 3, oSettings.oTexte.SepDecimal)

    Dim oRot As Matrix3d
    oRot = Matrix3dIdentity()
    On Error Resume Next
    If Not oSettings.oTextModele Is Nothing Then oRot = oSettings.oTextModele.Rotation
    On Error GoTo 0

    Dim oTxt As TextElement
    Dim bSansModele As Boolean
    On Error Resume Next
    Set oTxt = CreateTextElement1(oSettings.oTextModele, sAlt, oPtTexte, oRot)
    If oTxt Is Nothing Then
        Err.Clear
        bSansModele = True
        Set oTxt = CreateTextElement1(Nothing, sAlt, oPtTexte, oRot)
    End If
    On Error GoTo 0
    If bSansModele Or Not oSettings.oTexte.CommeModele Then
        oTxt.Color = oSettings.oTexte.Couleur
    End If
    oTxt.Redraw DrawMode
End Sub

'------------------------------------------------------------------------------
Private Sub CreerTexteEtCercle(oProj As Point3d, sAlt As String, _
                                oSettings As CMstSettings, oCalc As CInterpolation)
    ' oTextModele peut etre Nothing (cas ou P1 etait un tag) :
    ' CreateTextElement1 accepte Nothing comme modele (attributs actifs)
    Dim oRot As Matrix3d
    oRot = Matrix3dIdentity()
    On Error Resume Next
    If Not oSettings.oTextModele Is Nothing Then oRot = oSettings.oTextModele.Rotation
    On Error GoTo 0

    Dim oTxt As TextElement
    Dim bSansModele As Boolean
    On Error Resume Next
    Set oTxt = CreateTextElement1(oSettings.oTextModele, sAlt, oProj, oRot)
    If oTxt Is Nothing Then
        Err.Clear
        bSansModele = True
        Set oTxt = CreateTextElement1(Nothing, sAlt, oProj, oRot)
    End If
    On Error GoTo 0
    If bSansModele Or oSettings.oTextModele Is Nothing Or Not oSettings.oTexte.CommeModele Then
        oTxt.Color = oSettings.oTexte.Couleur
        Set oTxt.Level = ResolverNiveau(oSettings.oTexte.NomNiveau, oSettings)
    Else
        On Error Resume Next
        Dim sStyleC As String
        sStyleC = oSettings.oTextModele.TextStyle.Name
        If Err.Number = 0 And Len(sStyleC) > 0 Then
            Dim oStyleC As TextStyle
            Set oStyleC = ActiveDesignFile.TextStyles(sStyleC)
            If Not oStyleC Is Nothing Then
                oTxt.TextStyle = oStyleC
            End If
        End If
        Err.Clear
        Set oTxt.Level = ResolverNiveau(oSettings.oTexte.NomNiveau, oSettings)
        Err.Clear
        On Error GoTo 0
    End If
    ActiveModelReference.AddElement oTxt

    Dim oCercle As EllipseElement
    Set oCercle = CreateEllipseElement2(Nothing, oProj, _
                      oSettings.oCercle.Rayon, oSettings.oCercle.Rayon, Matrix3dIdentity())
    oCercle.Color = oSettings.oCercle.Couleur
    Set oCercle.Level = ResolverNiveau(oSettings.oCercle.NomNiveau, oSettings)
    ActiveModelReference.AddElement oCercle
End Sub

'------------------------------------------------------------------------------
Private Sub ClonerCellule(oSrc As CAltitudeSelection, oProj As Point3d, _
                          sAlt As String, oCalc As CInterpolation)
    ' Copier la cellule source dans le modele
    Dim oCopy As CellElement
    Set oCopy = ActiveModelReference.CopyElement(oSrc.oCellule)

    ' Deplacer vers le point projete
    Dim oVec As Point3d
    oVec.X = oProj.X - oSrc.oCellule.Origin.X
    oVec.Y = oProj.Y - oSrc.oCellule.Origin.Y
    ' Z aussi : le clone doit etre a l'altitude interpolee, pas a celle du
    ' point d'origine (oProj.Z porte le Z calcule).
    oVec.Z = oProj.Z - oSrc.oCellule.Origin.Z
    oCopy.Move oVec
    oCopy.Rewrite

    Dim bModifie As Boolean
    bModifie = False

    ' D'abord chercher un tag altitude (cas tag dans cellule)
    If Len(oSrc.TagDefName) > 0 Then
        Dim oSub1 As ElementEnumerator
        Set oSub1 = oCopy.GetSubElements
        Do While oSub1.MoveNext
            If oSub1.Current.Type = msdElementTypeTag Then
                Dim oTag As TagElement
                Set oTag = oSub1.Current
                If oTag.TagDefinitionName = oSrc.TagDefName Then
                    oTag.Value = sAlt
                    oTag.Rewrite
                    bModifie = True
                    Exit Do
                End If
            End If
        Loop
    End If

    ' Sinon chercher un texte altitude (cas cellule simple)
    If Not bModifie Then
        Dim oSub2 As ElementEnumerator
        Set oSub2 = oCopy.GetSubElements
        Do While oSub2.MoveNext
            If oSub2.Current.IsTextElement Then
                Dim oT As TextElement
                Set oT = oSub2.Current
                If oCalc.EstNombre(Replace(Trim$(oT.Text), ",", ".")) Then
                    oT.Text = sAlt
                    oT.Rewrite
                    Exit Do
                End If
            End If
        Loop
    End If
End Sub

'------------------------------------------------------------------------------
Private Sub ClonerTag(oSrc As CAltitudeSelection, oProj As Point3d, sAlt As String, _
                      oSettings As CMstSettings, oCalc As CInterpolation)
    ' Un tag MicroStation est toujours attache a un element hote via son
    ' BaseElement. Cloner le tag seul produit un orphelin (affiche en pointille).
    ' On copie donc l'hote, on le deplace, puis on reassocie un tag a la copie.
    ' Si le tag est reellement orphelin (pas d'hote), on cree un texte + cercle.

    ' 1) Recuperer l'hote via BaseElement (protege : peut lever ou etre Nothing)
    Dim oHost As Element
    Set oHost = Nothing
    On Error Resume Next
    Set oHost = oSrc.oTag.BaseElement
    On Error GoTo 0

    If oHost Is Nothing Then
        ' 3) Aucun hote : ne pas cloner un orphelin, fallback texte + cercle
        CreerTexteEtCercle oProj, sAlt, oSettings, oCalc
        Exit Sub
    End If

    ' Vecteur de deplacement (origine du tag source -> point projete)
    Dim oVec As Point3d
    oVec.X = oProj.X - oSrc.oTag.Origin.X
    oVec.Y = oProj.Y - oSrc.oTag.Origin.Y
    ' Z aussi : l'hote clone et son tag doivent etre a l'altitude interpolee,
    ' pas a celle du point d'origine (oProj.Z porte le Z calcule).
    oVec.Z = oProj.Z - oSrc.oTag.Origin.Z

    ' 2) Copier l'hote et le deplacer
    Dim oCopyHost As Element
    Set oCopyHost = ActiveModelReference.CopyElement(oHost)
    oCopyHost.Move oVec
    oCopyHost.Rewrite

    ' 2a) Approche A : copier le tag source, le deplacer, le reassocier a la copie
    Dim bOK As Boolean
    bOK = False
    On Error Resume Next
    Dim oCopyTag As TagElement
    Set oCopyTag = ActiveModelReference.CopyElement(oSrc.oTag)
    oCopyTag.Move oVec
    Set oCopyTag.BaseElement = oCopyHost
    oCopyTag.Value = sAlt
    oCopyTag.Rewrite
    If Err.Number = 0 And Not oCopyTag Is Nothing Then bOK = True
    On Error GoTo 0
    If bOK Then Exit Sub

    ' Approche A partielle : supprimer le tag copie (potentiellement orphelin)
    ' avant d'essayer l'approche B, pour ne pas laisser d'element parasite.
    On Error Resume Next
    If Not oCopyTag Is Nothing Then ActiveModelReference.RemoveElement oCopyTag
    On Error GoTo 0

    ' 2b) Approche B : recreer le tag via AddTag sur l'hote copie
    On Error Resume Next
    Dim oTagDef As TagDefinition
    Set oTagDef = TrouverTagDefinition(oSrc.oTag.TagDefinitionName)
    Dim oNewTag As TagElement
    If Not oTagDef Is Nothing Then
        Set oNewTag = oCopyHost.AddTag(oTagDef)
    End If
    If Not oNewTag Is Nothing Then
        ' Positionner le tag a l'emplacement du tag source deplace
        Dim oOrig As Point3d
        oOrig = oSrc.oTag.Origin
        Dim oVecTag As Point3d
        oVecTag.X = (oOrig.X + oVec.X) - oNewTag.Origin.X
        oVecTag.Y = (oOrig.Y + oVec.Y) - oNewTag.Origin.Y
        oVecTag.Z = (oOrig.Z + oVec.Z) - oNewTag.Origin.Z
        oNewTag.Move oVecTag

        ' Reprendre la symbologie et les attributs texte du tag source
        ' (AddTag cree le tag avec le style par defaut de la definition)
        CopierAttributsTag oSrc.oTag, oNewTag

        ' Seules la valeur et l'ecriture conditionnent la reussite : un echec
        ' de copie d'attribut ne doit pas declencher le fallback texte+cercle.
        Err.Clear
        oNewTag.Value = sAlt
        oNewTag.Rewrite
        bOK = (Err.Number = 0)
        If Not bOK Then ActiveModelReference.RemoveElement oNewTag
    End If
    On Error GoTo 0
    If bOK Then Exit Sub

    ' Dernier recours : texte + cercle pour ne pas laisser l'utilisateur sans point
    CreerTexteEtCercle oProj, sAlt, oSettings, oCalc
End Sub

'------------------------------------------------------------------------------
' Cherche une TagDefinition par nom en parcourant les TagSets du fichier actif.
' Renvoie Nothing si introuvable.
Private Function TrouverTagDefinition(sDefName As String) As TagDefinition
    Set TrouverTagDefinition = Nothing
    On Error Resume Next
    Dim oSet As TagSet
    Dim oDef As TagDefinition
    For Each oSet In ActiveDesignFile.TagSets
        For Each oDef In oSet.TagDefinitions
            If oDef.Name = sDefName Then
                Set TrouverTagDefinition = oDef
                Exit Function
            End If
        Next
    Next
    On Error GoTo 0
End Function

'------------------------------------------------------------------------------
' Copie la symbologie et les attributs texte (police, taille, justification)
' d'un tag source vers un tag cible. Les proprietes texte sont copiees en
' liaison tardive (Object) : selon la version de l'API certaines ne sont pas
' exposees par TagElement, et un acces en dur ne compilerait pas. L'echec
' d'une copie n'empeche pas les suivantes (Err.Clear apres chaque tentative).
Private Sub CopierAttributsTag(oSrc As TagElement, oDst As TagElement)
    On Error Resume Next

    ' Proprietes sures (exposees par TagElement)
    oDst.Color = oSrc.Color: Err.Clear
    Set oDst.Level = oSrc.Level: Err.Clear
    oDst.LineWeight = oSrc.LineWeight: Err.Clear
    ' oDst.Rotation = oSrc.Rotation: Err.Clear

    ' Proprietes texte incertaines : liaison tardive
    Dim oS As Object, oD As Object
    Set oS = oSrc
    Set oD = oDst
    Set oD.TextStyle = oS.TextStyle: Err.Clear
    Set oD.Font = oS.Font: Err.Clear
    oD.Height = oS.Height: Err.Clear
    oD.Width = oS.Width: Err.Clear
    oD.TextSize = oS.TextSize: Err.Clear
    oD.Justification = oS.Justification: Err.Clear

    On Error GoTo 0
End Sub

'==============================================================================
' Apercu dynamique (appele dans IPrimitiveCommandEvents_Dynamics)
'==============================================================================

'------------------------------------------------------------------------------
' Dessine l'apercu : ligne support, croix P1/P2, cercle et texte provisoires.
Sub DessinDynamique(ByVal DrawMode As MsdDrawingMode, _
                    oP1 As CPointRef, oP2 As CPointRef, _
                    oProj As Point3d, dT As Double, _
                    oSettings As CMstSettings, oCalc As CInterpolation)

    Dim dZInterp As Double
    dZInterp = oCalc.InterpolerZ(oP1.Altitude, oP2.Altitude, dT)

    ' Positions des points de reference en Point3d locaux
    ' Utilise Altitude plutot que Z de position (Z=0 si reference 2D)
    Dim oPt1 As Point3d, oPt2 As Point3d
    oP1.CopierPosition oPt1
    oP2.CopierPosition oPt2
    oPt1.Z = oP1.Altitude
    oPt2.Z = oP2.Altitude

    ' Ligne support P1-P2 etendue de 20% de chaque cote
    Dim dX As Double, dY As Double
    dX = oPt2.X - oPt1.X
    dY = oPt2.Y - oPt1.Y
    Dim oA As Point3d, oB As Point3d
    oA.X = oPt1.X - dX * 0.2: oA.Y = oPt1.Y - dY * 0.2: oA.Z = oPt1.Z
    oB.X = oPt2.X + dX * 0.2: oB.Y = oPt2.Y + dY * 0.2: oB.Z = oPt2.Z
    Dim oLigne As LineElement
    Set oLigne = CreateLineElement2(Nothing, oA, oB)
    oLigne.Color = 3
    oLigne.Redraw DrawMode

    ' Croix sur P1 et P2
    Dim dTailleCroix As Double
    dTailleCroix = oSettings.oCercle.Rayon * 0.8
    DessinCroix DrawMode, oPt1, dTailleCroix
    DessinCroix DrawMode, oPt2, dTailleCroix

    ' Perpendiculaire au point projete
    Dim dLen As Double
    dLen = Sqr(dX * dX + dY * dY)
    If dLen > 0.0000001 Then
        Dim dPerpLen As Double
        dPerpLen = dLen * 0.5
        Dim dPx As Double, dPy As Double
        dPx = -dY / dLen: dPy = dX / dLen
        Dim oPerpA As Point3d, oPerpB As Point3d
        oPerpA.X = oProj.X - dPerpLen * dPx: oPerpA.Y = oProj.Y - dPerpLen * dPy: oPerpA.Z = oProj.Z
        oPerpB.X = oProj.X + dPerpLen * dPx: oPerpB.Y = oProj.Y + dPerpLen * dPy: oPerpB.Z = oProj.Z
        Dim oLPerp As LineElement
        Set oLPerp = CreateLineElement2(Nothing, oPerpA, oPerpB)
        oLPerp.Color = 2
        oLPerp.Redraw DrawMode
    End If

    ' Cercle provisoire au point projete
    Dim oCercle As EllipseElement
    Set oCercle = CreateEllipseElement2(Nothing, oProj, _
                      oSettings.oCercle.Rayon, oSettings.oCercle.Rayon, Matrix3dIdentity())
    oCercle.Color = oSettings.oCercle.Couleur
    oCercle.Redraw DrawMode

    ' Texte altitude provisoire (meme position que la creation definitive)
    Dim sAlt As String
    sAlt = oCalc.FormatAltitude(dZInterp, 3, oSettings.oTexte.SepDecimal)
    Dim oRot As Matrix3d
    oRot = Matrix3dIdentity()
    On Error Resume Next
    oRot = oSettings.oTextModele.Rotation
    On Error GoTo 0
    Dim oTxt As TextElement
    On Error Resume Next
    Set oTxt = CreateTextElement1(oSettings.oTextModele, sAlt, oProj, oRot)
    If oTxt Is Nothing Then
        Err.Clear
        Set oTxt = CreateTextElement1(Nothing, sAlt, oProj, oRot)
    End If
    On Error GoTo 0
    If Not oSettings.oTexte.CommeModele Then
        oTxt.Color = oSettings.oTexte.Couleur
    End If
    oTxt.Redraw DrawMode
End Sub

'------------------------------------------------------------------------------
' Dessine l'apercu pour l'etape 2 : ligne P1-P2, croix, point projete fixe,
' ligne perpendiculaire et cercle+texte a la position decalee.
Sub DessinDecalage(ByVal DrawMode As MsdDrawingMode, _
                   oP1 As CPointRef, oP2 As CPointRef, _
                   oProj As Point3d, oPtDecale As Point3d, _
                   dZFinal As Double, dZSurDroite As Double, _
                   oSettings As CMstSettings, oCalc As CInterpolation)

    Dim oPt1 As Point3d, oPt2 As Point3d
    oP1.CopierPosition oPt1
    oP2.CopierPosition oPt2
    oPt1.Z = oP1.Altitude
    oPt2.Z = oP2.Altitude

    ' Ligne support P1-P2
    Dim dX As Double, dY As Double
    dX = oPt2.X - oPt1.X: dY = oPt2.Y - oPt1.Y
    Dim oA As Point3d, oB As Point3d
    oA.X = oPt1.X - dX * 0.2: oA.Y = oPt1.Y - dY * 0.2: oA.Z = oPt1.Z
    oB.X = oPt2.X + dX * 0.2: oB.Y = oPt2.Y + dY * 0.2: oB.Z = oPt2.Z
    Dim oLigne As LineElement
    Set oLigne = CreateLineElement2(Nothing, oA, oB)
    oLigne.Color = 3
    oLigne.Redraw DrawMode

    ' Croix sur P1, P2 et point projete
    Dim dTailleCroix As Double
    dTailleCroix = oSettings.oCercle.Rayon * 0.8
    DessinCroix DrawMode, oPt1, dTailleCroix
    DessinCroix DrawMode, oPt2, dTailleCroix
    DessinCroix DrawMode, oProj, dTailleCroix

    ' Ligne perpendiculaire depuis le point projete vers le point decale
    Dim oLPerp As LineElement
    Set oLPerp = CreateLineElement2(Nothing, oProj, oPtDecale)
    oLPerp.Color = 2
    oLPerp.Redraw DrawMode

    ' Cercle provisoire au point decale
    Dim oCercle As EllipseElement
    Set oCercle = CreateEllipseElement2(Nothing, oPtDecale, _
                      oSettings.oCercle.Rayon, oSettings.oCercle.Rayon, Matrix3dIdentity())
    oCercle.Color = oSettings.oCercle.Couleur
    oCercle.Redraw DrawMode

    Dim oRot As Matrix3d
    oRot = Matrix3dIdentity()
    On Error Resume Next
    oRot = oSettings.oTextModele.Rotation
    On Error GoTo 0

    ' Texte altitude au point decale (Z final)
    Dim sAltFinal As String
    sAltFinal = oCalc.FormatAltitude(dZFinal, 3, oSettings.oTexte.SepDecimal)
    Dim oTxt As TextElement
    On Error Resume Next
    Set oTxt = CreateTextElement1(oSettings.oTextModele, sAltFinal, oPtDecale, oRot)
    If oTxt Is Nothing Then
        Err.Clear
        Set oTxt = CreateTextElement1(Nothing, sAltFinal, oPtDecale, oRot)
    End If
    On Error GoTo 0
    If Not oSettings.oTexte.CommeModele Then
        oTxt.Color = oSettings.oTexte.Couleur
    End If
    oTxt.Redraw DrawMode

    ' Texte altitude au point projete sur la droite (Z interpole)
    Dim sAltDroite As String
    sAltDroite = oCalc.FormatAltitude(dZSurDroite, 3, oSettings.oTexte.SepDecimal)
    Dim oTxtDroite As TextElement
    On Error Resume Next
    Set oTxtDroite = CreateTextElement1(oSettings.oTextModele, sAltDroite, oProj, oRot)
    If oTxtDroite Is Nothing Then
        Err.Clear
        Set oTxtDroite = CreateTextElement1(Nothing, sAltDroite, oProj, oRot)
    End If
    On Error GoTo 0
    If Not oSettings.oTexte.CommeModele Then
        oTxtDroite.Color = oSettings.oTexte.Couleur
    End If
    oTxtDroite.Redraw DrawMode
End Sub

'==============================================================================
' Indicateur de pente (texte + fleche)
'==============================================================================

'------------------------------------------------------------------------------
' Apercu dynamique du texte pente + fleche au curseur.
Sub DessinPenteDynamique(ByVal DrawMode As MsdDrawingMode, _
                         oPtPlace As Point3d, _
                         oP1 As CPointRef, oP2 As CPointRef, _
                         oSettings As CMstSettings, oCalc As CInterpolation)

    Dim dPente As Double
    dPente = oCalc.PentePct(oP1, oP2)

    Dim sPente As String
    sPente = oCalc.FormatPente(dPente, oSettings.oTexte.SepDecimal, _
                               oSettings.oIndicPente.Decimales)

    Dim dDesX As Double, dDesY As Double
    DirectionP1P2 oP1, oP2, dDesX, dDesY

    ' Angle aligne sur la fleche (direction descente), ajuste pour lisibilite
    Dim dAngleTxt As Double
    dAngleTxt = oCalc.Angle2D(dDesX, dDesY)
    Const PI_D As Double = 3.14159265358979
    If dAngleTxt > PI_D / 2# Then dAngleTxt = dAngleTxt - PI_D
    If dAngleTxt < -PI_D / 2# Then dAngleTxt = dAngleTxt + PI_D

    Dim dTH As Double
    dTH = HauteurTexteModele(oSettings)

    Dim dPerpX As Double, dPerpY As Double
    dPerpX = -Sin(dAngleTxt): dPerpY = Cos(dAngleTxt)

    Dim oPtTxt As Point3d
    oPtTxt.X = oPtPlace.X + dPerpX * dTH * 0.8
    oPtTxt.Y = oPtPlace.Y + dPerpY * dTH * 0.8
    oPtTxt.Z = oPtPlace.Z

    Dim oRot As Matrix3d
    oRot = Matrix3dFromAxisAndRotationAngle(2, dAngleTxt)

    Dim oTxt As TextElement
    On Error Resume Next
    If oSettings.oIndicPente.Perso Then
        Set oTxt = CreateTextElement1(Nothing, sPente, oPtTxt, oRot)
        Dim oTSd As TextStyle: Set oTSd = oTxt.TextStyle
        oTSd.Height = oSettings.oIndicPente.Hauteur
        Dim dWD As Double: dWD = oSettings.oIndicPente.Largeur
        If dWD > 0 Then oTSd.Width = dWD Else oTSd.Width = oSettings.oIndicPente.Hauteur
        oTSd.Justification = msdTextJustificationLeftBottom
        Dim oTSdObj As Object: Set oTSdObj = oTSd
        oTSdObj.Background = False: Err.Clear
        oTxt.TextStyle = oTSd
        oTxt.Color = oSettings.oIndicPente.Couleur
    Else
        Set oTxt = CreateTextElement1(oSettings.oTextModele, sPente, oPtTxt, oRot)
        If oTxt Is Nothing Then
            Err.Clear
            Set oTxt = CreateTextElement1(Nothing, sPente, oPtTxt, oRot)
        End If
        Dim oTSm As TextStyle: Set oTSm = oTxt.TextStyle
        oTSm.Justification = msdTextJustificationLeftBottom
        oTxt.TextStyle = oTSm
        If Not oSettings.oTexte.CommeModele Then
            oTxt.Color = oSettings.oTexte.Couleur
        End If
    End If
    oTxt.Rotation = oRot
    Err.Clear
    On Error GoTo 0
    oTxt.Redraw DrawMode

    ' Fleche
    Dim oPtDeb As Point3d, oPtFin As Point3d
    Dim oPtH1 As Point3d, oPtH2 As Point3d
    GeometrieFleche oPtPlace, dDesX, dDesY, oSettings.oIndicPente.FlecheLongueur, _
                    oPtDeb, oPtFin, oPtH1, oPtH2

    Dim oL As LineElement
    Set oL = CreateLineElement2(Nothing, oPtDeb, oPtFin)
    oL.Color = oSettings.oIndicPente.FlecheCouleur
    oL.Redraw DrawMode

    Dim oLH1 As LineElement, oLH2 As LineElement
    Set oLH1 = CreateLineElement2(Nothing, oPtFin, oPtH1)
    oLH1.Color = oSettings.oIndicPente.FlecheCouleur
    oLH1.Redraw DrawMode
    Set oLH2 = CreateLineElement2(Nothing, oPtFin, oPtH2)
    oLH2.Color = oSettings.oIndicPente.FlecheCouleur
    oLH2.Redraw DrawMode
End Sub

'------------------------------------------------------------------------------
' Creation definitive du texte pente + fleche.
Sub CreerPente(oPtPlace As Point3d, _
               oP1 As CPointRef, oP2 As CPointRef, _
               oSettings As CMstSettings, oCalc As CInterpolation)

    Dim dPente As Double
    dPente = oCalc.PentePct(oP1, oP2)

    Dim sPente As String
    sPente = oCalc.FormatPente(dPente, oSettings.oTexte.SepDecimal, _
                               oSettings.oIndicPente.Decimales)

    Dim dDesX As Double, dDesY As Double
    DirectionP1P2 oP1, oP2, dDesX, dDesY

    Dim dAngleTxt As Double
    dAngleTxt = oCalc.Angle2D(dDesX, dDesY)
    Const PI_C As Double = 3.14159265358979
    If dAngleTxt > PI_C / 2# Then dAngleTxt = dAngleTxt - PI_C
    If dAngleTxt < -PI_C / 2# Then dAngleTxt = dAngleTxt + PI_C

    Dim dTH As Double
    dTH = HauteurTexteModele(oSettings)

    Dim dPerpX As Double, dPerpY As Double
    dPerpX = -Sin(dAngleTxt): dPerpY = Cos(dAngleTxt)

    Dim oPtTxt As Point3d
    oPtTxt.X = oPtPlace.X + dPerpX * dTH * 0.8
    oPtTxt.Y = oPtPlace.Y + dPerpY * dTH * 0.8
    oPtTxt.Z = oPtPlace.Z

    Dim oRot As Matrix3d
    oRot = Matrix3dFromAxisAndRotationAngle(2, dAngleTxt)

    Dim oTxt As TextElement
    On Error Resume Next
    If oSettings.oIndicPente.Perso Then
        Set oTxt = CreateTextElement1(Nothing, sPente, oPtTxt, oRot)
        Dim oTSc As TextStyle: Set oTSc = oTxt.TextStyle
        oTSc.Height = oSettings.oIndicPente.Hauteur
        Dim dWC As Double: dWC = oSettings.oIndicPente.Largeur
        If dWC > 0 Then oTSc.Width = dWC Else oTSc.Width = oSettings.oIndicPente.Hauteur
        oTSc.Justification = msdTextJustificationLeftBottom
        Dim oTScObj As Object: Set oTScObj = oTSc
        oTScObj.Background = False: Err.Clear
        oTxt.TextStyle = oTSc
        oTxt.Color = oSettings.oIndicPente.Couleur
        Set oTxt.Level = ResolverNiveau(oSettings.oIndicPente.NomNiveau, oSettings)
    Else
        Set oTxt = CreateTextElement1(oSettings.oTextModele, sPente, oPtTxt, oRot)
        If oTxt Is Nothing Then
            Err.Clear
            Set oTxt = CreateTextElement1(Nothing, sPente, oPtTxt, oRot)
        End If
        If oSettings.oTextModele Is Nothing Or Not oSettings.oTexte.CommeModele Then
            oTxt.Color = oSettings.oTexte.Couleur
            Set oTxt.Level = ResolverNiveau(oSettings.oTexte.NomNiveau, oSettings)
        Else
            Dim sStyleP As String
            sStyleP = oSettings.oTextModele.TextStyle.Name
            If Err.Number = 0 And Len(sStyleP) > 0 Then
                Dim oStyleP As TextStyle
                Set oStyleP = ActiveDesignFile.TextStyles(sStyleP)
                If Not oStyleP Is Nothing Then
                    oTxt.TextStyle = oStyleP
                End If
            End If
            Err.Clear
            Set oTxt.Level = ResolverNiveau(oSettings.oTexte.NomNiveau, oSettings)
            Err.Clear
        End If
        Dim oTSp As TextStyle: Set oTSp = oTxt.TextStyle
        oTSp.Justification = msdTextJustificationLeftBottom
        oTxt.TextStyle = oTSp
    End If
    oTxt.Rotation = oRot
    Err.Clear
    On Error GoTo 0
    ActiveModelReference.AddElement oTxt

    ' Fleche permanente
    Dim oPtDeb As Point3d, oPtFin As Point3d
    Dim oPtH1 As Point3d, oPtH2 As Point3d
    GeometrieFleche oPtPlace, dDesX, dDesY, oSettings.oIndicPente.FlecheLongueur, _
                    oPtDeb, oPtFin, oPtH1, oPtH2

    Dim oLvl As Level
    Set oLvl = ResolverNiveau(oSettings.oTexte.NomNiveau, oSettings)

    Dim oL As LineElement
    Set oL = CreateLineElement2(Nothing, oPtDeb, oPtFin)
    oL.Color = oSettings.oIndicPente.FlecheCouleur
    Set oL.Level = oLvl
    ActiveModelReference.AddElement oL

    Dim oLH1 As LineElement, oLH2 As LineElement
    Set oLH1 = CreateLineElement2(Nothing, oPtFin, oPtH1)
    oLH1.Color = oSettings.oIndicPente.FlecheCouleur
    Set oLH1.Level = oLvl
    ActiveModelReference.AddElement oLH1
    Set oLH2 = CreateLineElement2(Nothing, oPtFin, oPtH2)
    oLH2.Color = oSettings.oIndicPente.FlecheCouleur
    Set oLH2.Level = oLvl
    ActiveModelReference.AddElement oLH2
End Sub

'==============================================================================
' Utilitaires prives
'==============================================================================

Private Sub DessinCroix(ByVal DrawMode As MsdDrawingMode, oPt As Point3d, dTaille As Double)
    Dim oA As Point3d, oB As Point3d, oL As LineElement

    oA.X = oPt.X - dTaille: oA.Y = oPt.Y: oA.Z = oPt.Z
    oB.X = oPt.X + dTaille: oB.Y = oPt.Y: oB.Z = oPt.Z
    Set oL = CreateLineElement2(Nothing, oA, oB)
    oL.Color = 3: oL.Redraw DrawMode

    oA.X = oPt.X: oA.Y = oPt.Y - dTaille
    oB.X = oPt.X: oB.Y = oPt.Y + dTaille
    Set oL = CreateLineElement2(Nothing, oA, oB)
    oL.Color = 3: oL.Redraw DrawMode
End Sub

'------------------------------------------------------------------------------
' Resout un niveau par nom ou numero ; chaine vide ou niveau introuvable =
' niveau du texte-modele P1. Sert au cercle comme au texte personnalise.
Private Function ResolverNiveau(sNiveau As String, oSettings As CMstSettings) As Level
    Set ResolverNiveau = ActiveSettings.Level

    If Not oSettings.oTextModele Is Nothing Then
        On Error Resume Next
        Dim sModNiv As String
        sModNiv = oSettings.oTextModele.Level.Name
        If Err.Number = 0 And Len(sModNiv) > 0 Then
            Dim oLvlMod As Level
            Set oLvlMod = ActiveDesignFile.Levels(sModNiv)
            If Err.Number = 0 And Not oLvlMod Is Nothing Then
                Set ResolverNiveau = oLvlMod
            End If
        End If
        Err.Clear
        On Error GoTo 0
    End If

    If sNiveau = "" Then Exit Function

    Dim oLvl As Level
    On Error Resume Next
    Set oLvl = ActiveDesignFile.Levels(sNiveau)
    On Error GoTo 0
    If oLvl Is Nothing And IsNumeric(sNiveau) Then
        Dim oL As Level
        For Each oL In ActiveDesignFile.Levels
            If oL.Number = CLng(Val(sNiveau)) Then
                Set oLvl = oL: Exit For
            End If
        Next
    End If
    If Not oLvl Is Nothing Then Set ResolverNiveau = oLvl
End Function

'------------------------------------------------------------------------------
' Direction unitaire de P1 vers P2.
Private Sub DirectionP1P2(oP1 As CPointRef, oP2 As CPointRef, _
                           dDirX As Double, dDirY As Double)
    Dim dX As Double, dY As Double, dLen As Double
    ' Fleche dans le sens de la descente (du plus haut vers le plus bas)
    If oP1.Altitude >= oP2.Altitude Then
        dX = oP2.X - oP1.X: dY = oP2.Y - oP1.Y
    Else
        dX = oP1.X - oP2.X: dY = oP1.Y - oP2.Y
    End If
    dLen = Sqr(dX * dX + dY * dY)
    If dLen < 0.0000001 Then
        dDirX = 1#: dDirY = 0#
        Exit Sub
    End If
    dDirX = dX / dLen: dDirY = dY / dLen
End Sub


'------------------------------------------------------------------------------
' Calcule les 4 points d'une fleche centree sur oPtCentre.
' oPtDeb/oPtFin = extremites du corps, oPtH1/oPtH2 = pointe de fleche.
Private Sub GeometrieFleche(oPtCentre As Point3d, _
                             dDirX As Double, dDirY As Double, _
                             dLongueur As Double, _
                             oPtDeb As Point3d, oPtFin As Point3d, _
                             oPtH1 As Point3d, oPtH2 As Point3d)
    Dim dHL As Double
    dHL = dLongueur / 2#

    oPtDeb.X = oPtCentre.X - dDirX * dHL
    oPtDeb.Y = oPtCentre.Y - dDirY * dHL
    oPtDeb.Z = oPtCentre.Z
    oPtFin.X = oPtCentre.X + dDirX * dHL
    oPtFin.Y = oPtCentre.Y + dDirY * dHL
    oPtFin.Z = oPtCentre.Z

    Dim dHeadLen As Double
    dHeadLen = dLongueur * 0.2
    Const HEAD_ANGLE As Double = 0.4363

    oPtH1.X = oPtFin.X - dHeadLen * (dDirX * Cos(HEAD_ANGLE) - dDirY * Sin(HEAD_ANGLE))
    oPtH1.Y = oPtFin.Y - dHeadLen * (dDirX * Sin(HEAD_ANGLE) + dDirY * Cos(HEAD_ANGLE))
    oPtH1.Z = oPtFin.Z

    oPtH2.X = oPtFin.X - dHeadLen * (dDirX * Cos(HEAD_ANGLE) + dDirY * Sin(HEAD_ANGLE))
    oPtH2.Y = oPtFin.Y - dHeadLen * (-dDirX * Sin(HEAD_ANGLE) + dDirY * Cos(HEAD_ANGLE))
    oPtH2.Z = oPtFin.Z
End Sub


'------------------------------------------------------------------------------
' Hauteur du texte modele P1 (fallback 0.1 u.m.).
Private Function HauteurTexteModele(oSettings As CMstSettings) As Double
    If oSettings.oIndicPente.Perso Then
        HauteurTexteModele = oSettings.oIndicPente.Hauteur
    ElseIf oSettings.dModeleHauteur > 0 Then
        HauteurTexteModele = oSettings.dModeleHauteur
    Else
        HauteurTexteModele = 0.1
    End If
End Function

Attribute VB_Name = "CMstSettings"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CMstSettings - Parametres de la commande Interpolation Topo V2
'
' Agregateur unique des parametres, regroupes par domaine :
'   oTexte      : symbologie et format du texte altitude
'   oCercle     : symbologie du cercle
'   oIndicPente : indicateur de pente (texte + fleche)
'   oDecalage   : pente transversale + DZ fixe (interpolation)
'   oChemin     : pente + DZ du chemin principal (ponctuelle)
'   oRayon      : pente + DZ du rayonnement (ponctuelle)
'
' Instancie une seule fois dans le module principal.
' Passe en parametre aux classes qui en ont besoin (CMoteurGraphique, etc.).
'==============================================================================
Option Explicit

Public oTexte           As CSymboTexte      ' symbologie et format du texte
Public oCercle          As CSymboCercle     ' symbologie du cercle
Public oIndicPente      As CSymboPente      ' indicateur de pente (texte + fleche)
Public oDecalage        As CParamPenteDZ    ' interpolation : pente transversale + DZ fixe
Public oChemin          As CParamPenteDZ    ' ponctuelle : chemin principal
Public oRayon           As CParamPenteDZ    ' ponctuelle : rayonnement
Public dTolTexte        As Double           ' rayon de recherche autour du clic (u.m.)
Public oTextModele      As TextElement      ' element P1 : modele pour CreateTextElement1
Public oTagModele       As TagElement       ' tag P1 : modele quand la source est un tag
Public dModeleHauteur   As Double           ' hauteur du texte source (0 = non defini)
Public nPonctDecimales  As Integer          ' ponctuelle : decimales des points crees (chemin + rayon)
Public bRayonIndicPente As Boolean          ' ponctuelle : placer pente+fleche apres chaque rayon
Public bCheminIndicPente As Boolean         ' ponctuelle : placer pente+fleche apres chaque point chemin
Public bDecalIndicPente As Boolean          ' interpolation : placer pente+fleche apres un point decale (pente transversale)

'------------------------------------------------------------------------------
Sub Init()
    Set oTexte = New CSymboTexte
    Set oCercle = New CSymboCercle
    oCercle.InitDefauts
    Set oIndicPente = New CSymboPente
    oIndicPente.InitDefauts
    Set oDecalage = New CParamPenteDZ
    Set oChemin = New CParamPenteDZ
    Set oRayon = New CParamPenteDZ
    dTolTexte = 1#
    Set oTextModele = Nothing
    Set oTagModele = Nothing
    dModeleHauteur = 0#
    nPonctDecimales = 2
End Sub

'------------------------------------------------------------------------------
' Appele apres la selection de P1 : charge le texte-modele et ses attributs.
' L'indicateur de pente herite de la hauteur/largeur/couleur du texte P1.
Sub ChargerModeleTexte(oText As TextElement, sSep As String, nDec As Integer)
    Set oTextModele = oText
    Set oTagModele = Nothing
    oTexte.ChargerDepuisElement oText
    oTexte.SepDecimal = sSep
    oTexte.Decimales = nDec
    On Error Resume Next
    Dim oTemp As TextElement
    Dim ptO As Point3d
    Set oTemp = CreateTextElement1(oText, "0", ptO, Matrix3dIdentity())
    If Not oTemp Is Nothing Then
        dModeleHauteur = CDbl(oTemp.TextStyle.Height)
        oIndicPente.Largeur = CDbl(oTemp.TextStyle.Width)
    Else
        Err.Clear
        dModeleHauteur = CDbl(oText.TextStyle.Height)
        oIndicPente.Largeur = CDbl(oText.TextStyle.Width)
    End If
    oIndicPente.Hauteur = dModeleHauteur
    If oIndicPente.Largeur <= 0 Then oIndicPente.Largeur = dModeleHauteur
    oIndicPente.Couleur = oText.Color
    If Err.Number <> 0 Then
        dModeleHauteur = 0#
        oIndicPente.Hauteur = 0.1
        oIndicPente.Largeur = 0.1
    End If
    SyncStyleTexteModele oText
    Err.Clear
    On Error GoTo 0
End Sub

'------------------------------------------------------------------------------
' Cree le style de texte du modele dans le fichier actif s'il n'existe pas.
' Le background est active en deux temps pour que MicroStation initialise
' correctement la couleur de fond (comme un toggle manuel dans la UI).
Private Sub SyncStyleTexteModele(oText As TextElement)
    On Error Resume Next
    Dim oSrcTS As TextStyle
    Set oSrcTS = oText.TextStyle
    If oSrcTS Is Nothing Then Exit Sub

    Dim sNom As String
    sNom = oSrcTS.Name
    If Err.Number <> 0 Or Len(sNom) = 0 Then Err.Clear: Exit Sub

    Dim oExist As TextStyle
    Set oExist = Nothing
    Set oExist = ActiveDesignFile.TextStyles(sNom)
    If Not oExist Is Nothing Then Err.Clear: Exit Sub

    Err.Clear
    Dim oNew As TextStyle
    Set oNew = ActiveDesignFile.TextStyles.Add(Nothing, sNom)
    If oNew Is Nothing Then Err.Clear: Exit Sub

    oNew.Height = oSrcTS.Height
    oNew.Width = oSrcTS.Width
    Set oNew.Font = oSrcTS.Font
    oNew.Color = oSrcTS.Color

    Dim oNewObj As Object, oSrcObj As Object
    Set oNewObj = oNew
    Set oSrcObj = oSrcTS

    Dim bSrcBg As Boolean
    bSrcBg = False
    bSrcBg = CBool(oSrcObj.Background)
    Err.Clear

    If bSrcBg Then
        oNewObj.Background = False
        Err.Clear
        oNewObj.Background = True
        Err.Clear
    End If

    Err.Clear
    On Error GoTo 0
End Sub

'------------------------------------------------------------------------------
' Appele quand la source P1 est un tag : estime la hauteur depuis le Range.
Sub ChargerModeleDepuisTag(oTag As TagElement, sSep As String, nDec As Integer)
    Set oTagModele = oTag
    oTexte.SepDecimal = sSep
    oTexte.Decimales = nDec
    dModeleHauteur = 0#
    On Error Resume Next
    Dim oRng As Range3d
    oRng = oTag.Range
    Dim ptL As Point3d, ptH As Point3d
    ptL = oRng.Low: ptH = oRng.High
    Dim dHY As Double, dHX As Double
    dHY = Abs(ptH.Y - ptL.Y)
    dHX = Abs(ptH.X - ptL.X)
    If dHY > 0 And dHX > 0 Then
        If dHX < dHY Then dModeleHauteur = dHX Else dModeleHauteur = dHY
    End If
    If dModeleHauteur > 0 Then
        oIndicPente.Hauteur = dModeleHauteur
        oIndicPente.Largeur = dModeleHauteur
    End If
    oIndicPente.Couleur = oTag.Color
    Err.Clear
    On Error GoTo 0
End Sub

'------------------------------------------------------------------------------
Sub AjusterDecimales(nDecP2 As Integer)
    If nDecP2 > oTexte.Decimales Then oTexte.Decimales = nDecP2
End Sub

'------------------------------------------------------------------------------
' Vrai si le texte-modele est disponible (P1 a ete selectionne)
Property Get TextModeleDisponible() As Boolean
    TextModeleDisponible = Not (oTextModele Is Nothing)
End Property

Attribute VB_Name = "CParamPenteDZ"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CParamPenteDZ - Couple pente (%) + decalage fixe DZ, chacun activable
'
' Utilise trois fois par CMstSettings :
'   oDecalage : pente transversale + DZ fixe (interpolation)
'   oChemin   : chemin principal (ponctuelle)
'   oRayon    : rayonnement (ponctuelle)
'
' Les membres valent 0 / False par defaut (initialisation VBA), ce qui
' correspond aux valeurs de depart voulues : rien n'est applique.
'==============================================================================
Option Explicit

Public Pente        As Double    ' pente en %
Public PenteActive  As Boolean   ' True = appliquer la pente
Public DZ           As Double    ' decalage fixe en Z (u.m.)
Public DZActive     As Boolean   ' True = appliquer le decalage DZ

Attribute VB_Name = "CPlacerChemin"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPlacerChemin - Interpolation le long d'un chemin defini par l'utilisateur
'
' Apres selection et snap de P1 et P2, l'utilisateur construit un chemin :
'   Data  = ajouter un point intermediaire au chemin
'   Reset = valider le chemin et creer les elements topo
'           (si aucun point : retour a la selection de P1)
'
' Chemin final : P1 -> points intermediaires -> P2
' Altitude de chaque point interpolee lineairement :
'   Z(Pi) = Z(P1) + (dist_cumulee(Pi) / dist_totale) * (Z(P2) - Z(P1))
'==============================================================================
Option Explicit

Implements IPrimitiveCommandEvents

Private m_dPtsX() As Double
Private m_dPtsY() As Double
Private m_nPts As Long

Private Sub IPrimitiveCommandEvents_Start()
    ShowCommand "Interpolation Topo"
    ShowPrompt "CHEMIN : cliquez pour placer le 1er point intermediaire  (Reset=nouvelle selection)"
    m_nPts = 0
    ReDim m_dPtsX(0 To 0)
    ReDim m_dPtsY(0 To 0)
    CommandState.StartDynamics
End Sub

Private Sub IPrimitiveCommandEvents_Dynamics(Point As Point3d, ByVal View As View, _
                                             ByVal DrawMode As MsdDrawingMode)
    On Error Resume Next
    Dim oPt1 As Point3d, oPt2 As Point3d
    Dim dTailleCroix As Double
    Dim dTotalDist As Double, dCursorDist As Double
    Dim dPrevX As Double, dPrevY As Double, dPrevZ As Double
    Dim dCumDist As Double, dSegDist As Double
    Dim dT As Double, dZi As Double, dTCursor As Double, dZCursor As Double
    Dim oPtA As Point3d, oPtB As Point3d, oPtC As Point3d, oPtCur As Point3d
    Dim oLigne As LineElement
    Dim oCercle As EllipseElement
    Dim sAltI As String, sAltCur As String
    Dim i As Long

    g_oP1.CopierPosition oPt1
    g_oP2.CopierPosition oPt2
    dTailleCroix = g_oSettings.oCercle.Rayon * 0.8

    ' --- Distance totale du chemin P1 -> pts intermediaires -> curseur -> P2 ---
    dPrevX = oPt1.X: dPrevY = oPt1.Y
    dTotalDist = 0

    For i = 0 To m_nPts - 1
        dTotalDist = dTotalDist + DistXY(dPrevX, dPrevY, m_dPtsX(i), m_dPtsY(i))
        dPrevX = m_dPtsX(i): dPrevY = m_dPtsY(i)
    Next i

    dCursorDist = dTotalDist + DistXY(dPrevX, dPrevY, Point.X, Point.Y)
    dTotalDist = dCursorDist + DistXY(Point.X, Point.Y, oPt2.X, oPt2.Y)

    ' --- Segments places (vert) avec croix et texte altitude ---
    dPrevX = oPt1.X: dPrevY = oPt1.Y: dPrevZ = g_oP1.Altitude
    dCumDist = 0

    For i = 0 To m_nPts - 1
        dSegDist = DistXY(dPrevX, dPrevY, m_dPtsX(i), m_dPtsY(i))
        dCumDist = dCumDist + dSegDist

        If dTotalDist > 0.0001 Then dT = dCumDist / dTotalDist Else dT = 0
        dZi = g_oCalc.InterpolerZ(g_oP1.Altitude, g_oP2.Altitude, dT)
        If g_oSettings.oDecalage.DZActive Then dZi = dZi + g_oSettings.oDecalage.DZ

        oPtA.X = dPrevX: oPtA.Y = dPrevY: oPtA.Z = dPrevZ
        oPtB.X = m_dPtsX(i): oPtB.Y = m_dPtsY(i): oPtB.Z = dZi

        Set oLigne = CreateLineElement2(Nothing, oPtA, oPtB)
        oLigne.Color = 2
        oLigne.Redraw DrawMode

        DessinCroixLocal DrawMode, oPtB, dTailleCroix

        sAltI = g_oCalc.FormatAltitude(dZi, 3, g_oSettings.oTexte.SepDecimal)
        DessinTexteProvLocal DrawMode, oPtB, sAltI

        dPrevX = m_dPtsX(i): dPrevY = m_dPtsY(i): dPrevZ = dZi
    Next i

    ' --- Z interpole au curseur ---
    If dTotalDist > 0.0001 Then dTCursor = dCursorDist / dTotalDist Else dTCursor = 0
    dZCursor = g_oCalc.InterpolerZ(g_oP1.Altitude, g_oP2.Altitude, dTCursor)
    If g_oSettings.oDecalage.DZActive Then dZCursor = dZCursor + g_oSettings.oDecalage.DZ

    ' --- Segment dynamique : dernier point -> curseur (jaune) ---
    oPtC.X = dPrevX: oPtC.Y = dPrevY: oPtC.Z = dPrevZ
    oPtCur.X = Point.X: oPtCur.Y = Point.Y: oPtCur.Z = dZCursor

    Set oLigne = CreateLineElement2(Nothing, oPtC, oPtCur)
    oLigne.Color = 4
    oLigne.Redraw DrawMode

    ' --- Segment dynamique : curseur -> P2 (jaune) ---
    Set oLigne = CreateLineElement2(Nothing, oPtCur, oPt2)
    oLigne.Color = 4
    oLigne.Redraw DrawMode

    ' --- Croix P1 et P2 ---
    DessinCroixLocal DrawMode, oPt1, dTailleCroix
    DessinCroixLocal DrawMode, oPt2, dTailleCroix

    ' --- Cercle + texte au curseur ---
    Set oCercle = CreateEllipseElement2(Nothing, oPtCur, _
                      g_oSettings.oCercle.Rayon, g_oSettings.oCercle.Rayon, Matrix3dIdentity())
    oCercle.Color = g_oSettings.oCercle.Couleur
    oCercle.Redraw DrawMode

    sAltCur = g_oCalc.FormatAltitude(dZCursor, 3, g_oSettings.oTexte.SepDecimal)
    DessinTexteProvLocal DrawMode, oPtCur, sAltCur

    ' --- Barre d'etat ---
    If m_nPts = 0 Then
        ShowPrompt "CHEMIN : Z=" & sAltCur & _
                   "  Data=placer 1er point  Reset=nouvelle selection"
    Else
        ShowPrompt "CHEMIN : Z=" & sAltCur & _
                   "  Dist=" & Format$(dCursorDist, "0.00") & "/" & _
                   Format$(dTotalDist, "0.00") & _
                   "  (" & m_nPts & " pts)  Data=ajouter  Reset=valider"
    End If
    On Error GoTo 0
End Sub

Private Sub IPrimitiveCommandEvents_DataPoint(Point As Point3d, ByVal View As View)
    If m_nPts > 0 Then
        ReDim Preserve m_dPtsX(0 To m_nPts)
        ReDim Preserve m_dPtsY(0 To m_nPts)
    End If
    m_dPtsX(m_nPts) = Point.X
    m_dPtsY(m_nPts) = Point.Y
    m_nPts = m_nPts + 1

    ShowPrompt "CHEMIN : point " & m_nPts & " ajoute  |  " & _
               "Data=ajouter  Reset=valider le chemin"
End Sub

Private Sub IPrimitiveCommandEvents_Keyin(ByVal Keyin As String)
End Sub

Private Sub IPrimitiveCommandEvents_Reset()
    If m_nPts = 0 Then
        frmInterpolation.ReinitialiserEtat
        ShowPrompt "Nouvelle selection : cliquez pres du texte altitude du POINT 1  (Reset=quitter)"
        CommandState.StartPrimitive New CSelectP1
        Exit Sub
    End If

    Dim oPt1 As Point3d, oPt2 As Point3d
    Dim dTotalDist As Double
    Dim dPrevX As Double, dPrevY As Double
    Dim dCumDist As Double
    Dim dT As Double, DZ As Double
    Dim oPt As Point3d
    Dim i As Long
    Dim nCreated As Long

    g_oP1.CopierPosition oPt1
    g_oP2.CopierPosition oPt2

    ' Distance totale : P1 -> points -> P2
    dPrevX = oPt1.X: dPrevY = oPt1.Y
    dTotalDist = 0

    For i = 0 To m_nPts - 1
        dTotalDist = dTotalDist + DistXY(dPrevX, dPrevY, m_dPtsX(i), m_dPtsY(i))
        dPrevX = m_dPtsX(i): dPrevY = m_dPtsY(i)
    Next i
    dTotalDist = dTotalDist + DistXY(dPrevX, dPrevY, oPt2.X, oPt2.Y)

    If dTotalDist < 0.0001 Then
        ShowPrompt "Chemin trop court - ajoutez des points plus eloignes"
        Exit Sub
    End If

    ' Creation des elements a chaque point intermediaire
    dPrevX = oPt1.X: dPrevY = oPt1.Y
    dCumDist = 0

    On Error Resume Next
    For i = 0 To m_nPts - 1
        dCumDist = dCumDist + DistXY(dPrevX, dPrevY, m_dPtsX(i), m_dPtsY(i))

        dT = dCumDist / dTotalDist
        DZ = g_oCalc.InterpolerZ(g_oP1.Altitude, g_oP2.Altitude, dT)
        If g_oSettings.oDecalage.DZActive Then DZ = DZ + g_oSettings.oDecalage.DZ

        oPt.X = m_dPtsX(i)
        oPt.Y = m_dPtsY(i)
        oPt.Z = DZ

        g_oMoteur.CreerPointTopo oPt, DZ, g_oSettings, g_oCalc

        dPrevX = m_dPtsX(i): dPrevY = m_dPtsY(i)
    Next i
    On Error GoTo 0

    nCreated = m_nPts

    ' Reinitialiser pour un eventuel nouveau chemin
    m_nPts = 0
    ReDim m_dPtsX(0 To 0)
    ReDim m_dPtsY(0 To 0)

    ShowPrompt "Chemin valide : " & nCreated & " points crees  |  " & _
               "Data=nouveau chemin  Reset=nouvelle selection"
End Sub

Private Sub IPrimitiveCommandEvents_Cleanup()
End Sub

'==============================================================================
' Utilitaires prives
'==============================================================================

Private Function DistXY(dX1 As Double, dY1 As Double, _
                         dX2 As Double, dY2 As Double) As Double
    DistXY = Sqr((dX2 - dX1) ^ 2 + (dY2 - dY1) ^ 2)
End Function

Private Sub DessinCroixLocal(ByVal DrawMode As MsdDrawingMode, _
                              oPt As Point3d, dTaille As Double)
    Dim oA As Point3d, oB As Point3d, oL As LineElement

    oA.X = oPt.X - dTaille: oA.Y = oPt.Y: oA.Z = oPt.Z
    oB.X = oPt.X + dTaille: oB.Y = oPt.Y: oB.Z = oPt.Z
    Set oL = CreateLineElement2(Nothing, oA, oB)
    oL.Color = 3: oL.Redraw DrawMode

    oA.X = oPt.X: oA.Y = oPt.Y - dTaille
    oB.X = oPt.X: oB.Y = oPt.Y + dTaille
    Set oL = CreateLineElement2(Nothing, oA, oB)
    oL.Color = 3: oL.Redraw DrawMode
End Sub

Private Sub DessinTexteProvLocal(ByVal DrawMode As MsdDrawingMode, _
                                  oPt As Point3d, sAlt As String)
    Dim oRot As Matrix3d
    Dim oTxt As TextElement

    oRot = Matrix3dIdentity()
    On Error Resume Next
    If Not g_oSettings.oTextModele Is Nothing Then oRot = g_oSettings.oTextModele.Rotation
    On Error GoTo 0

    On Error Resume Next
    Set oTxt = CreateTextElement1(g_oSettings.oTextModele, sAlt, oPt, oRot)
    If oTxt Is Nothing Then
        Err.Clear
        Set oTxt = CreateTextElement1(Nothing, sAlt, oPt, oRot)
    End If
    On Error GoTo 0
    If Not g_oSettings.oTexte.CommeModele Then
        oTxt.Color = g_oSettings.oTexte.Couleur
    End If
    oTxt.Redraw DrawMode
End Sub

Attribute VB_Name = "CPlacerPente"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPlacerPente - Placement dynamique du texte pente + fleche
'
' Apres snap P2, l'utilisateur clique pour placer l'indicateur de pente.
'   Data  = placer le texte pente + fleche a la position du curseur
'   Reset = revenir a la selection de P1
' La fleche pointe dans la direction de descente (du plus haut vers le plus bas).
'==============================================================================
Option Explicit

Implements IPrimitiveCommandEvents

Private Sub IPrimitiveCommandEvents_Start()
    ShowCommand "Interpolation Topo"
    ShowPrompt "Pente=" & g_oCalc.FormatPente(g_oCalc.PentePct(g_oP1, g_oP2), _
               g_oSettings.oTexte.SepDecimal) & _
               "  |  Cliquez pour placer pente + fleche  (Reset=nouv. selection)"
    CommandState.StartDynamics
End Sub

Private Sub IPrimitiveCommandEvents_Dynamics(Point As Point3d, ByVal View As View, _
                                             ByVal DrawMode As MsdDrawingMode)
    On Error Resume Next
    g_oMoteur.DessinPenteDynamique DrawMode, Point, g_oP1, g_oP2, g_oSettings, g_oCalc
    On Error GoTo 0
End Sub

Private Sub IPrimitiveCommandEvents_DataPoint(Point As Point3d, ByVal View As View)
    g_oMoteur.CreerPente Point, g_oP1, g_oP2, g_oSettings, g_oCalc

    ShowPrompt "Pente placee  |  " & _
               g_oCalc.FormatPente(g_oCalc.PentePct(g_oP1, g_oP2), _
               g_oSettings.oTexte.SepDecimal) & _
               "  Data=placer encore  Reset=nouv. selection"
End Sub

Private Sub IPrimitiveCommandEvents_Keyin(ByVal Keyin As String)
End Sub

Private Sub IPrimitiveCommandEvents_Reset()
    frmInterpolation.ReinitialiserEtat
    ShowPrompt "Nouvelle selection : cliquez pres du texte altitude du POINT 1  (Reset=quitter)"
    CommandState.StartPrimitive New CSelectP1
End Sub

Private Sub IPrimitiveCommandEvents_Cleanup()
End Sub

Attribute VB_Name = "CPlacerPenteReseau"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPlacerPenteReseau - Placement du texte pente + fleche entre deux BoiteEP
'
' Reutilise g_oMoteur.DessinPenteDynamique / g_oMoteur.CreerPente pour ne pas
' dupliquer la geometrie de la fleche ni le rendu du texte pente : g_oRefFeP1
' et g_oRefFeP2 (alimentes par les Fe) tiennent lieu de couple P1/P2 topo.
'
'   Dynamics = apercu texte+fleche a la position du curseur
'   Data     = creation definitive + auto-chainage : P2 devient P1 et on
'              retourne au snap du POINT 2 (regard suivant du reseau)
'   Reset    = retour au snap POINT 1 (nouvelle selection independante)
'==============================================================================
Option Explicit

Implements IPrimitiveCommandEvents

Private Sub IPrimitiveCommandEvents_Start()
    ShowCommand "Pente Reseau EU/EP"
    ShowPrompt "Pente=" & g_oCalc.FormatPente( _
               g_oCalc.PentePct(g_oRefFeP1, g_oRefFeP2), _
               g_oSettings.oTexte.SepDecimal, _
               g_oSettings.oIndicPente.Decimales) & _
               "  |  cliquez pour placer texte+fleche  (Reset=nouv. selection)"
    CommandState.StartDynamics
End Sub

Private Sub IPrimitiveCommandEvents_Dynamics(Point As Point3d, ByVal View As View, _
                                             ByVal DrawMode As MsdDrawingMode)
    On Error Resume Next

    ' Ligne provisoire P1_snap -> P2_snap (visuelle uniquement, ne persiste pas)
    Dim ptL1 As Point3d, ptL2 As Point3d
    ptL1 = g_ptSnapP1: ptL1.Z = Point.Z
    ptL2 = g_ptSnapP2: ptL2.Z = Point.Z
    Dim oL As LineElement
    Set oL = CreateLineElement2(Nothing, ptL1, ptL2)
    oL.Color = 3
    oL.Redraw msdDrawingModeTemporary

    ' Apercu texte pente + fleche
    g_oMoteur.DessinPenteDynamique DrawMode, Point, _
                                   g_oRefFeP1, g_oRefFeP2, g_oSettings, g_oCalc
    On Error GoTo 0
End Sub

Private Sub IPrimitiveCommandEvents_DataPoint(Point As Point3d, ByVal View As View)
    ' 1) Creer texte pente + fleche definitifs
    g_oMoteur.CreerPente Point, g_oRefFeP1, g_oRefFeP2, g_oSettings, g_oCalc

    ' 2) Auto-chainage : le regard P2 devient le nouveau P1
    g_oBoiteP1.CopierDepuis g_oBoiteP2
    g_ptSnapP1 = g_ptSnapP2
    AlimenterPointRefFeSnap g_oRefFeP1, g_ptSnapP1, g_oBoiteP1

    ' 3) Preparer un P2 propre
    g_oBoiteP2.Vider
    g_oRefFeP2.Valide = False

    ' 4) Mise a jour du formulaire (P1 = ex-P2, P2 vide)
    frmReseauEP.AfficherBoiteP1 g_oBoiteP1
    frmReseauEP.EffacerP2

    ' 5) On repart directement au snap du regard suivant
    ShowPrompt "Pente placee. P1 = ex-P2 (" & DecrireBoite(g_oBoiteP1) & _
               ")  |  snappez le POINT 2 suivant  (Reset = nouv. selection)"
    CommandState.StartPrimitive New CSnapBoiteP2
End Sub

Private Sub IPrimitiveCommandEvents_Keyin(ByVal Keyin As String)
End Sub

Private Sub IPrimitiveCommandEvents_Reset()
    frmReseauEP.ReinitialiserEtat
    ShowPrompt "Nouvelle selection : snappez le POINT 1  (Reset=quitter)"
    CommandState.StartPrimitive New CSnapBoiteP1
End Sub

Private Sub IPrimitiveCommandEvents_Cleanup()
End Sub

Attribute VB_Name = "CPlacerPoint"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPlacerPoint V2 - Etat commande : placement dynamique du point interpole
'
' Etape 1 : projection sur P1-P2 + decalage perpendiculaire simultane
'           => Data = creer le cercle (et texte si cellule/tag)
' Etape 2 : placement libre du texte altitude => Data = creer le texte
'   (cellule/tag : etape 2 sautee, tout est cree en etape 1)
' Etape 3 : placement pente + fleche du segment transversal (projection -> point)
'   si "Appliquer pente transversale" et "Pente + fleche" sont coches
'   Data = placer l'indicateur, Reset = le sauter ; retour etape 1
' Reset (etapes 1-2) = revenir a la selection de P1
'==============================================================================
Option Explicit

Implements IPrimitiveCommandEvents

Private m_nEtape        As Integer      ' 1=projection+perpendiculaire, 2=texte libre, 3=pente+fleche
Private m_dZFinal       As Double       ' altitude finale pour le texte (etape 2)
Private m_dProjX        As Double       ' projection sur P1-P2 (X) du dernier point cree
Private m_dProjY        As Double       ' projection sur P1-P2 (Y)
Private m_dZInterp      As Double       ' altitude interpolee sur la droite (projection)
Private m_dPtX          As Double       ' dernier point cree (X)
Private m_dPtY          As Double       ' dernier point cree (Y)
Private m_bPenteApres   As Boolean      ' True = placer pente+fleche apres le point/texte

Private Sub IPrimitiveCommandEvents_Start()
    ShowCommand "Interpolation Topo"
    ShowPrompt g_oCalc.InfoSegment(g_oP1, g_oP2) & _
               "  |  Deplacez le curseur : Data=placer le point  Reset=nouv. selection"
    m_nEtape = 1
    CommandState.StartDynamics
End Sub

Private Sub IPrimitiveCommandEvents_Dynamics(Point As Point3d, ByVal View As View, _
                                             ByVal DrawMode As MsdDrawingMode)
    Select Case m_nEtape
    Case 1
        ' --- Projection sur P1-P2 + decalage perpendiculaire simultane ---
        Dim dT As Double, oProj As Point3d
        g_oCalc.ProjecterSurSegment g_oP1, g_oP2, Point, dT, oProj

        Dim dZInterp As Double
        dZInterp = g_oCalc.InterpolerZ(g_oP1.Altitude, g_oP2.Altitude, dT)

        Dim dX As Double, dY As Double, dLen As Double
        dX = g_oP2.X - g_oP1.X
        dY = g_oP2.Y - g_oP1.Y
        dLen = Sqr(dX * dX + dY * dY)
        Dim dPerpX As Double, dPerpY As Double
        If dLen > 0.0000001 Then
            dPerpX = -dY / dLen
            dPerpY = dX / dLen
        Else
            dPerpX = 0: dPerpY = 1
        End If

        Dim dOffset As Double
        dOffset = (Point.X - oProj.X) * dPerpX + (Point.Y - oProj.Y) * dPerpY

        Dim oPtDecale As Point3d
        oPtDecale.X = oProj.X + dOffset * dPerpX
        oPtDecale.Y = oProj.Y + dOffset * dPerpY

        Dim dZFinal As Double
        dZFinal = dZInterp
        If g_oSettings.oDecalage.PenteActive Then
            dZFinal = dZFinal + Abs(dOffset) * g_oSettings.oDecalage.Pente / 100#
        End If
        If g_oSettings.oDecalage.DZActive Then dZFinal = dZFinal + g_oSettings.oDecalage.DZ
        oPtDecale.Z = dZFinal

        g_oMoteur.DessinDecalage DrawMode, g_oP1, g_oP2, oProj, oPtDecale, _
                                  dZFinal, dZInterp, g_oSettings, g_oCalc

        Dim sZDroite As String, sZFinal As String
        sZDroite = g_oCalc.FormatAltitude(dZInterp, 3, g_oSettings.oTexte.SepDecimal)
        sZFinal = g_oCalc.FormatAltitude(dZFinal, 3, g_oSettings.oTexte.SepDecimal)

        Dim sPrompt As String
        If Abs(dOffset) < 0.001 Then
            sPrompt = "Z=" & sZDroite & "  t=" & Format$(dT, "0.000")
        Else
            sPrompt = "Z(droite)=" & sZDroite & "  Z(final)=" & sZFinal & _
                       "  dec=" & Format$(dOffset, "0.000") & _
                       "  t=" & Format$(dT, "0.000")
        End If

        If dT < 0# Or dT > 1# Then
            sPrompt = sPrompt & "  HORS SEGMENT"
        End If
        sPrompt = sPrompt & "  (Data=placer  Reset=nouv. selection)"
        ShowPrompt sPrompt

    Case 2
        ' --- Etape 2 : placement libre du texte ---
        g_oMoteur.DessinTexteLibre DrawMode, Point, m_dZFinal, g_oSettings, g_oCalc

        Dim sAlt3 As String
        sAlt3 = g_oCalc.FormatAltitude(m_dZFinal, 3, g_oSettings.oTexte.SepDecimal)
        ShowPrompt "Placez le texte Z=" & sAlt3 & _
                   "  (Data=poser le texte  Reset=nouv. selection)"

    Case 3
        ' --- Etape 3 : placement pente + fleche du segment transversal ---
        Dim oRefP As New CPointRef, oRefD As New CPointRef
        InitRefPenteTransv oRefP, oRefD
        On Error Resume Next
        g_oMoteur.DessinPenteDynamique DrawMode, Point, oRefP, oRefD, g_oSettings, g_oCalc
        On Error GoTo 0
        ShowPrompt "Placez la pente + fleche  (Data=poser  Reset=sauter)"
    End Select
End Sub

Private Sub IPrimitiveCommandEvents_DataPoint(Point As Point3d, ByVal View As View)
    Select Case m_nEtape
    Case 1
        ' --- Creer le point a la position calculee ---
        Dim dT As Double, oProj As Point3d
        g_oCalc.ProjecterSurSegment g_oP1, g_oP2, Point, dT, oProj

        Dim dZInterp As Double
        dZInterp = g_oCalc.InterpolerZ(g_oP1.Altitude, g_oP2.Altitude, dT)

        Dim dX As Double, dY As Double, dLen As Double
        dX = g_oP2.X - g_oP1.X
        dY = g_oP2.Y - g_oP1.Y
        dLen = Sqr(dX * dX + dY * dY)
        Dim dPerpX As Double, dPerpY As Double
        If dLen > 0.0000001 Then
            dPerpX = -dY / dLen
            dPerpY = dX / dLen
        Else
            dPerpX = 0: dPerpY = 1
        End If

        Dim dOffset As Double
        dOffset = (Point.X - oProj.X) * dPerpX + (Point.Y - oProj.Y) * dPerpY

        Dim oPtDecale As Point3d
        oPtDecale.X = oProj.X + dOffset * dPerpX
        oPtDecale.Y = oProj.Y + dOffset * dPerpY

        Dim dZFinal As Double
        dZFinal = dZInterp
        If g_oSettings.oDecalage.PenteActive Then
            dZFinal = dZFinal + Abs(dOffset) * g_oSettings.oDecalage.Pente / 100#
        End If
        If g_oSettings.oDecalage.DZActive Then dZFinal = dZFinal + g_oSettings.oDecalage.DZ
        oPtDecale.Z = dZFinal

        ' Memoriser le segment transversal pour l'indicateur pente + fleche
        m_dProjX = oProj.X: m_dProjY = oProj.Y: m_dZInterp = dZInterp
        m_dPtX = oPtDecale.X: m_dPtY = oPtDecale.Y
        m_dZFinal = dZFinal
        m_bPenteApres = g_oSettings.oDecalage.PenteActive And _
                        g_oSettings.bDecalIndicPente And Abs(dOffset) > 0.001

        If SourceP1Integree() Then
            g_oMoteur.CreerPointTopo oPtDecale, dZFinal, g_oSettings, g_oCalc

            Dim sAlt1 As String
            sAlt1 = g_oCalc.FormatAltitude(dZFinal, g_oSettings.oTexte.Decimales, _
                                             g_oSettings.oTexte.SepDecimal)
            If m_bPenteApres Then
                ShowPrompt "Point cree Z=" & sAlt1 & _
                           "  |  Placez la pente + fleche  (Data=poser  Reset=sauter)"
                m_nEtape = 3
            Else
                ShowPrompt "Point cree Z=" & sAlt1 & _
                           "  |  Data = autre point, Reset = nouvelle selection"
            End If
        Else
            g_oMoteur.CreerCercleSeul oPtDecale, g_oSettings

            Dim sAlt2 As String
            sAlt2 = g_oCalc.FormatAltitude(dZFinal, g_oSettings.oTexte.Decimales, _
                                             g_oSettings.oTexte.SepDecimal)
            ShowPrompt "Cercle cree Z=" & sAlt2 & _
                       "  |  Placez le texte altitude  (Data=poser  Reset=nouv. selection)"
            m_nEtape = 2
        End If

    Case 2
        ' --- Poser le texte a la position choisie ---
        Point.Z = m_dZFinal
        g_oMoteur.CreerTexteSeul Point, m_dZFinal, g_oSettings, g_oCalc

        Dim sAlt3 As String
        sAlt3 = g_oCalc.FormatAltitude(m_dZFinal, g_oSettings.oTexte.Decimales, _
                                        g_oSettings.oTexte.SepDecimal)
        If m_bPenteApres Then
            ShowPrompt "Point cree Z=" & sAlt3 & _
                       "  |  Placez la pente + fleche  (Data=poser  Reset=sauter)"
            m_nEtape = 3
        Else
            ShowPrompt "Point cree Z=" & sAlt3 & _
                       "  |  Data = autre point sur la meme droite, Reset = nouvelle selection"
            m_nEtape = 1
        End If

    Case 3
        ' --- Placer l'indicateur pente + fleche du segment transversal ---
        Dim oRefP3 As New CPointRef, oRefD3 As New CPointRef
        InitRefPenteTransv oRefP3, oRefD3
        g_oMoteur.CreerPente Point, oRefP3, oRefD3, g_oSettings, g_oCalc
        ShowPrompt "Pente placee  |  Data = autre point, Reset = nouvelle selection"
        m_nEtape = 1
    End Select
End Sub

Private Sub IPrimitiveCommandEvents_Keyin(ByVal Keyin As String)
End Sub

' Reset = nouvelle selection de P1 (etape 3 : sauter l'indicateur pente)
Private Sub IPrimitiveCommandEvents_Reset()
    If m_nEtape = 3 Then
        ShowPrompt "Data = autre point, Reset = nouvelle selection"
        m_nEtape = 1
        Exit Sub
    End If
    frmInterpolation.ReinitialiserEtat
    ShowPrompt "Nouvelle selection : cliquez pres du texte altitude du POINT 1  (Reset=quitter)"
    CommandState.StartPrimitive New CSelectP1
End Sub

Private Sub IPrimitiveCommandEvents_Cleanup()
End Sub

'------------------------------------------------------------------------------
' Refs du segment transversal : projection sur P1-P2 -> point decale cree
Private Sub InitRefPenteTransv(oRefProj As CPointRef, oRefPoint As CPointRef)
    oRefProj.X = m_dProjX: oRefProj.Y = m_dProjY
    oRefProj.Z = m_dZInterp: oRefProj.Altitude = m_dZInterp
    oRefProj.Valide = True
    oRefPoint.X = m_dPtX: oRefPoint.Y = m_dPtY
    oRefPoint.Z = m_dZFinal: oRefPoint.Altitude = m_dZFinal
    oRefPoint.Valide = True
End Sub

'------------------------------------------------------------------------------
Private Function SourceP1Integree() As Boolean
    SourceP1Integree = False
    If g_oSelectionP1 Is Nothing Then Exit Function
    If g_oSelectionP1.EstReference Then Exit Function
    SourceP1Integree = (Not g_oSelectionP1.oCellule Is Nothing) Or _
                       (Not g_oSelectionP1.oTag Is Nothing)
End Function

Attribute VB_Name = "CPlacerPonctuel"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPlacerPonctuel - Machine a etats : chemin principal + rayonnement
'
' Etape 1 (CHEMIN) : ligne dynamique depuis le dernier point
'   Data  = creer le point (Z = dernier Z + pente*dist + DZ chemin)
'   Reset = nouvelle selection P1
' Etape 2 (TEXTE CHEMIN) : placement libre du texte altitude
'   Data  = poser le texte, passer en mode rayonnement
' Etape 3 (RAYONNEMENT) : ligne dynamique depuis le point chemin
'   Data  = creer un point rayon (Z = centre Z + pente*dist + DZ rayon)
'   Reset = terminer rayonnement, repartir en chemin depuis ce point
' Etape 4 (TEXTE RAYON) : placement libre du texte altitude rayon
'   Data  = poser le texte, revenir en rayonnement (ou etape 5)
' Etape 5 (PENTE RAYON) : placement pente + fleche du rayon
'   Data  = placer l'indicateur, revenir en rayonnement
'   Reset = sauter l'indicateur, revenir en rayonnement
' Etape 6 (PENTE CHEMIN) : placement pente + fleche du segment chemin
'   Data  = placer l'indicateur, passer en rayonnement
'   Reset = sauter l'indicateur, passer en rayonnement
'
' Pour les cellules/tags, les etapes texte (2 et 4) sont sautees.
'==============================================================================
Option Explicit

Implements IPrimitiveCommandEvents

Private m_nEtape        As Integer      ' 1..6
Private m_dLastX        As Double       ' position du dernier point chemin (X)
Private m_dLastY        As Double       ' position du dernier point chemin (Y)
Private m_dLastZ        As Double       ' altitude du dernier point chemin
Private m_dPrevX        As Double       ' point chemin precedent (X) pour la pente
Private m_dPrevY        As Double       ' point chemin precedent (Y)
Private m_dPrevZ        As Double       ' altitude du point chemin precedent
Private m_dCentreX      As Double       ' centre rayonnement (X) = dernier point chemin
Private m_dCentreY      As Double       ' centre rayonnement (Y)
Private m_dCentreZ      As Double       ' centre rayonnement (Z)
Private m_dZFinal       As Double       ' altitude figee pour le placement texte
Private m_dRayonX       As Double       ' position du dernier rayon (X)
Private m_dRayonY       As Double       ' position du dernier rayon (Y)
Private m_dRayonZ       As Double       ' altitude du dernier rayon

Private Sub IPrimitiveCommandEvents_Start()
    ShowCommand "Interpol. Ponctuelle"

    ' Initialiser la position de depart depuis P1
    Dim oPt1 As Point3d
    g_oP1.CopierPosition oPt1
    m_dLastX = oPt1.X
    m_dLastY = oPt1.Y
    m_dLastZ = g_oP1.Altitude

    m_nEtape = 1
    ShowPrompt "CHEMIN depuis P1 (Z=" & Format$(m_dLastZ, "0.000") & _
               ")  Data=placer un point  Reset=nouv. selection"
    CommandState.StartDynamics
End Sub

Private Sub IPrimitiveCommandEvents_Dynamics(Point As Point3d, ByVal View As View, _
                                             ByVal DrawMode As MsdDrawingMode)
    Select Case m_nEtape
    Case 1
        DessinChemin DrawMode, Point

    Case 2
        g_oMoteur.DessinTexteLibre DrawMode, Point, m_dZFinal, g_oSettings, g_oCalc
        Dim sA2 As String
        sA2 = g_oCalc.FormatAltitude(m_dZFinal, 3, g_oSettings.oTexte.SepDecimal)
        ShowPrompt "Placez le texte Z=" & sA2 & _
                   "  (Data=poser  Reset=nouv. selection)"

    Case 3
        DessinRayon DrawMode, Point

    Case 4
        g_oMoteur.DessinTexteLibre DrawMode, Point, m_dZFinal, g_oSettings, g_oCalc
        Dim sA4 As String
        sA4 = g_oCalc.FormatAltitude(m_dZFinal, 3, g_oSettings.oTexte.SepDecimal)
        ShowPrompt "Placez le texte rayon Z=" & sA4 & _
                   "  (Data=poser  Reset=nouv. selection)"

    Case 5
        Dim oRefC As New CPointRef, oRefR As New CPointRef
        InitRefPente oRefC, oRefR
        On Error Resume Next
        g_oMoteur.DessinPenteDynamique DrawMode, Point, oRefC, oRefR, g_oSettings, g_oCalc
        On Error GoTo 0
        ShowPrompt "Placez la pente + fleche  (Data=poser  Reset=sauter)"

    Case 6
        Dim oRefA As New CPointRef, oRefB As New CPointRef
        InitRefPenteChemin oRefA, oRefB
        On Error Resume Next
        g_oMoteur.DessinPenteDynamique DrawMode, Point, oRefA, oRefB, g_oSettings, g_oCalc
        On Error GoTo 0
        ShowPrompt "Placez la pente + fleche du chemin  (Data=poser  Reset=sauter)"
    End Select
End Sub

Private Sub IPrimitiveCommandEvents_DataPoint(Point As Point3d, ByVal View As View)
    Select Case m_nEtape
    Case 1
        ' --- Creer un point chemin ---
        Dim dDist As Double, dZNew As Double
        dDist = DistXYLocal(m_dLastX, m_dLastY, Point.X, Point.Y)
        dZNew = m_dLastZ
        If g_oSettings.oChemin.PenteActive Then
            dZNew = dZNew + dDist * g_oSettings.oChemin.Pente / 100#
        End If
        If g_oSettings.oChemin.DZActive Then dZNew = dZNew + g_oSettings.oChemin.DZ

        Dim oPtChem As Point3d
        oPtChem.X = Point.X: oPtChem.Y = Point.Y: oPtChem.Z = dZNew

        If SourceP1Integree() Then
            g_oMoteur.CreerPointTopo oPtChem, dZNew, g_oSettings, g_oCalc
            AvancerChemin oPtChem.X, oPtChem.Y, dZNew
            If g_oSettings.bCheminIndicPente Then
                EntrerPenteChemin
            Else
                EntrerRayonnement dZNew
            End If
        Else
            g_oMoteur.CreerCercleSeul oPtChem, g_oSettings
            m_dZFinal = dZNew
            m_dCentreX = oPtChem.X: m_dCentreY = oPtChem.Y: m_dCentreZ = dZNew
            Dim sAC As String
            sAC = g_oCalc.FormatAltitude(dZNew, g_oSettings.nPonctDecimales, _
                                          g_oSettings.oTexte.SepDecimal)
            ShowPrompt "Cercle cree Z=" & sAC & _
                       "  |  Placez le texte altitude (Data=poser  Reset=nouv. selection)"
            m_nEtape = 2
        End If

    Case 2
        ' --- Poser le texte chemin ---
        Point.Z = m_dZFinal
        g_oMoteur.CreerTexteSeul Point, m_dZFinal, g_oSettings, g_oCalc
        AvancerChemin m_dCentreX, m_dCentreY, m_dZFinal
        If g_oSettings.bCheminIndicPente Then
            EntrerPenteChemin
        Else
            EntrerRayonnement m_dZFinal
        End If

    Case 3
        ' --- Creer un point rayonnement ---
        Dim dDistR As Double, dZRay As Double
        dDistR = DistXYLocal(m_dCentreX, m_dCentreY, Point.X, Point.Y)
        dZRay = m_dCentreZ
        If g_oSettings.oRayon.PenteActive Then
            dZRay = dZRay + dDistR * g_oSettings.oRayon.Pente / 100#
        End If
        If g_oSettings.oRayon.DZActive Then dZRay = dZRay + g_oSettings.oRayon.DZ

        Dim oPtRay As Point3d
        oPtRay.X = Point.X: oPtRay.Y = Point.Y: oPtRay.Z = dZRay

        m_dRayonX = oPtRay.X: m_dRayonY = oPtRay.Y: m_dRayonZ = dZRay

        If SourceP1Integree() Then
            g_oMoteur.CreerPointTopo oPtRay, dZRay, g_oSettings, g_oCalc
            Dim sAR1 As String
            sAR1 = g_oCalc.FormatAltitude(dZRay, g_oSettings.nPonctDecimales, _
                                            g_oSettings.oTexte.SepDecimal)
            If g_oSettings.bRayonIndicPente Then
                ShowPrompt "Rayon Z=" & sAR1 & _
                           "  |  Placez la pente + fleche  (Data=poser  Reset=sauter)"
                m_nEtape = 5
            Else
                ShowPrompt "Rayon cree Z=" & sAR1 & _
                           "  |  Data=autre rayon  Reset=continuer chemin"
            End If
        Else
            g_oMoteur.CreerCercleSeul oPtRay, g_oSettings
            m_dZFinal = dZRay
            Dim sAR2 As String
            sAR2 = g_oCalc.FormatAltitude(dZRay, g_oSettings.nPonctDecimales, _
                                            g_oSettings.oTexte.SepDecimal)
            ShowPrompt "Cercle rayon Z=" & sAR2 & _
                       "  |  Placez le texte (Data=poser  Reset=nouv. selection)"
            m_nEtape = 4
        End If

    Case 4
        ' --- Poser le texte rayonnement ---
        Point.Z = m_dZFinal
        g_oMoteur.CreerTexteSeul Point, m_dZFinal, g_oSettings, g_oCalc
        If g_oSettings.bRayonIndicPente Then
            ShowPrompt "Placez la pente + fleche  (Data=poser  Reset=sauter)"
            m_nEtape = 5
        Else
            Dim sAR3 As String
            sAR3 = g_oCalc.FormatAltitude(m_dZFinal, g_oSettings.nPonctDecimales, _
                                            g_oSettings.oTexte.SepDecimal)
            ShowPrompt "Rayon cree Z=" & sAR3 & _
                       "  |  Data=autre rayon  Reset=continuer chemin"
            m_nEtape = 3
        End If

    Case 5
        ' --- Placer l'indicateur pente + fleche du rayon ---
        Dim oRefC5 As New CPointRef, oRefR5 As New CPointRef
        InitRefPente oRefC5, oRefR5
        g_oMoteur.CreerPente Point, oRefC5, oRefR5, g_oSettings, g_oCalc
        ShowPrompt "Pente placee  |  Data=autre rayon  Reset=continuer chemin"
        m_nEtape = 3

    Case 6
        ' --- Placer l'indicateur pente + fleche du segment chemin ---
        Dim oRefA6 As New CPointRef, oRefB6 As New CPointRef
        InitRefPenteChemin oRefA6, oRefB6
        g_oMoteur.CreerPente Point, oRefA6, oRefB6, g_oSettings, g_oCalc
        EntrerRayonnement m_dLastZ
    End Select
End Sub

Private Sub IPrimitiveCommandEvents_Keyin(ByVal Keyin As String)
End Sub

Private Sub IPrimitiveCommandEvents_Reset()
    Select Case m_nEtape
    Case 1, 2
        ' Reset en chemin = nouvelle selection P1
        frmInterpolPonct.ReinitialiserEtat
        ShowPrompt "Nouvelle selection : cliquez pres du texte altitude du POINT 1  (Reset=quitter)"
        Dim oEtat As New CSelectP1
        oEtat.Mode = modePonctuelle
        CommandState.StartPrimitive oEtat

    Case 3, 4
        ' Reset en rayonnement = repartir en chemin depuis le centre
        m_dLastX = m_dCentreX: m_dLastY = m_dCentreY: m_dLastZ = m_dCentreZ
        m_nEtape = 1
        ShowPrompt "CHEMIN depuis Z=" & Format$(m_dLastZ, "0.000") & _
                   "  Data=placer un point  Reset=nouv. selection"

    Case 5
        ' Reset en pente = sauter l'indicateur, revenir en rayonnement
        ShowPrompt "Data=autre rayon  Reset=continuer chemin"
        m_nEtape = 3

    Case 6
        ' Reset en pente chemin = sauter l'indicateur, passer en rayonnement
        EntrerRayonnement m_dLastZ
    End Select
End Sub

Private Sub IPrimitiveCommandEvents_Cleanup()
End Sub

'==============================================================================
' Dessin dynamique
'==============================================================================

Private Sub DessinChemin(ByVal DrawMode As MsdDrawingMode, oPtCurseur As Point3d)
    Dim dDist As Double, dZNew As Double
    dDist = DistXYLocal(m_dLastX, m_dLastY, oPtCurseur.X, oPtCurseur.Y)
    dZNew = m_dLastZ
    If g_oSettings.oChemin.PenteActive Then
        dZNew = dZNew + dDist * g_oSettings.oChemin.Pente / 100#
    End If
    If g_oSettings.oChemin.DZActive Then dZNew = dZNew + g_oSettings.oChemin.DZ

    ' Ligne depuis dernier point vers curseur
    Dim oPtDep As Point3d, oPtArr As Point3d
    oPtDep.X = m_dLastX: oPtDep.Y = m_dLastY: oPtDep.Z = m_dLastZ
    oPtArr.X = oPtCurseur.X: oPtArr.Y = oPtCurseur.Y: oPtArr.Z = dZNew

    Dim oLigne As LineElement
    Set oLigne = CreateLineElement2(Nothing, oPtDep, oPtArr)
    oLigne.Color = 2
    oLigne.Redraw DrawMode

    ' Croix sur le point de depart
    Dim dTaille As Double
    dTaille = g_oSettings.oCercle.Rayon * 0.8
    DessinCroixLocal DrawMode, oPtDep, dTaille

    ' Cercle + texte provisoire au curseur
    Dim oCercle As EllipseElement
    Set oCercle = CreateEllipseElement2(Nothing, oPtArr, _
                      g_oSettings.oCercle.Rayon, g_oSettings.oCercle.Rayon, Matrix3dIdentity())
    oCercle.Color = g_oSettings.oCercle.Couleur
    oCercle.Redraw DrawMode

    Dim sAlt As String
    sAlt = g_oCalc.FormatAltitude(dZNew, 3, g_oSettings.oTexte.SepDecimal)
    DessinTexteProvLocal DrawMode, oPtArr, sAlt

    ShowPrompt "CHEMIN  Z=" & sAlt & "  dist=" & Format$(dDist, "0.000") & _
               "  (Data=placer  Reset=nouv. selection)"
End Sub

Private Sub DessinRayon(ByVal DrawMode As MsdDrawingMode, oPtCurseur As Point3d)
    Dim dDist As Double, dZRay As Double
    dDist = DistXYLocal(m_dCentreX, m_dCentreY, oPtCurseur.X, oPtCurseur.Y)
    dZRay = m_dCentreZ
    If g_oSettings.oRayon.PenteActive Then
        dZRay = dZRay + dDist * g_oSettings.oRayon.Pente / 100#
    End If
    If g_oSettings.oRayon.DZActive Then dZRay = dZRay + g_oSettings.oRayon.DZ

    ' Ligne depuis le centre vers le curseur
    Dim oPtC As Point3d, oPtR As Point3d
    oPtC.X = m_dCentreX: oPtC.Y = m_dCentreY: oPtC.Z = m_dCentreZ
    oPtR.X = oPtCurseur.X: oPtR.Y = oPtCurseur.Y: oPtR.Z = dZRay

    Dim oLigne As LineElement
    Set oLigne = CreateLineElement2(Nothing, oPtC, oPtR)
    oLigne.Color = 4
    oLigne.Redraw DrawMode

    ' Croix sur le centre
    Dim dTaille As Double
    dTaille = g_oSettings.oCercle.Rayon * 0.8
    DessinCroixLocal DrawMode, oPtC, dTaille

    ' Cercle + texte provisoire au curseur
    Dim oCercle As EllipseElement
    Set oCercle = CreateEllipseElement2(Nothing, oPtR, _
                      g_oSettings.oCercle.Rayon, g_oSettings.oCercle.Rayon, Matrix3dIdentity())
    oCercle.Color = g_oSettings.oCercle.Couleur
    oCercle.Redraw DrawMode

    Dim sAlt As String
    sAlt = g_oCalc.FormatAltitude(dZRay, 3, g_oSettings.oTexte.SepDecimal)
    DessinTexteProvLocal DrawMode, oPtR, sAlt

    ShowPrompt "RAYON  Z=" & sAlt & "  dist=" & Format$(dDist, "0.000") & _
               "  (Data=placer  Reset=continuer chemin)"
End Sub

'==============================================================================
' Utilitaires prives
'==============================================================================

Private Sub AvancerChemin(dX As Double, dY As Double, DZ As Double)
    m_dPrevX = m_dLastX: m_dPrevY = m_dLastY: m_dPrevZ = m_dLastZ
    m_dLastX = dX: m_dLastY = dY: m_dLastZ = DZ
End Sub

Private Sub EntrerPenteChemin()
    m_nEtape = 6
    ShowPrompt "Placez la pente + fleche du chemin  (Data=poser  Reset=sauter)"
End Sub

Private Sub EntrerRayonnement(DZ As Double)
    m_dCentreX = m_dLastX: m_dCentreY = m_dLastY: m_dCentreZ = DZ
    m_nEtape = 3
    Dim sZ As String
    sZ = g_oCalc.FormatAltitude(DZ, g_oSettings.nPonctDecimales, _
                                 g_oSettings.oTexte.SepDecimal)
    ShowPrompt "RAYON depuis Z=" & sZ & _
               "  Data=placer un rayon  Reset=continuer chemin"
End Sub

Private Function DistXYLocal(dX1 As Double, dY1 As Double, _
                              dX2 As Double, dY2 As Double) As Double
    DistXYLocal = Sqr((dX2 - dX1) ^ 2 + (dY2 - dY1) ^ 2)
End Function

Private Sub DessinCroixLocal(ByVal DrawMode As MsdDrawingMode, _
                              oPt As Point3d, dTaille As Double)
    Dim oA As Point3d, oB As Point3d, oL As LineElement
    oA.X = oPt.X - dTaille: oA.Y = oPt.Y: oA.Z = oPt.Z
    oB.X = oPt.X + dTaille: oB.Y = oPt.Y: oB.Z = oPt.Z
    Set oL = CreateLineElement2(Nothing, oA, oB)
    oL.Color = 3: oL.Redraw DrawMode
    oA.X = oPt.X: oA.Y = oPt.Y - dTaille
    oB.X = oPt.X: oB.Y = oPt.Y + dTaille
    Set oL = CreateLineElement2(Nothing, oA, oB)
    oL.Color = 3: oL.Redraw DrawMode
End Sub

Private Sub DessinTexteProvLocal(ByVal DrawMode As MsdDrawingMode, _
                                  oPt As Point3d, sAlt As String)
    Dim oRot As Matrix3d
    oRot = Matrix3dIdentity()
    On Error Resume Next
    If Not g_oSettings.oTextModele Is Nothing Then oRot = g_oSettings.oTextModele.Rotation
    On Error GoTo 0
    Dim oTxt As TextElement
    On Error Resume Next
    Set oTxt = CreateTextElement1(g_oSettings.oTextModele, sAlt, oPt, oRot)
    If oTxt Is Nothing Then
        Err.Clear
        Set oTxt = CreateTextElement1(Nothing, sAlt, oPt, oRot)
    End If
    On Error GoTo 0
    If Not g_oSettings.oTexte.CommeModele Then
        oTxt.Color = g_oSettings.oTexte.Couleur
    End If
    oTxt.Redraw DrawMode
End Sub

Private Function SourceP1Integree() As Boolean
    SourceP1Integree = False
    If g_oSelectionP1 Is Nothing Then Exit Function
    If g_oSelectionP1.EstReference Then Exit Function
    SourceP1Integree = (Not g_oSelectionP1.oCellule Is Nothing) Or _
                       (Not g_oSelectionP1.oTag Is Nothing)
End Function

Private Sub InitRefPenteChemin(oRefPrev As CPointRef, oRefNew As CPointRef)
    oRefPrev.X = m_dPrevX: oRefPrev.Y = m_dPrevY
    oRefPrev.Z = m_dPrevZ: oRefPrev.Altitude = m_dPrevZ
    oRefPrev.Valide = True
    oRefNew.X = m_dLastX: oRefNew.Y = m_dLastY
    oRefNew.Z = m_dLastZ: oRefNew.Altitude = m_dLastZ
    oRefNew.Valide = True
End Sub

Private Sub InitRefPente(oRefCentre As CPointRef, oRefRayon As CPointRef)
    oRefCentre.X = m_dCentreX: oRefCentre.Y = m_dCentreY
    oRefCentre.Z = m_dCentreZ: oRefCentre.Altitude = m_dCentreZ
    oRefCentre.Valide = True
    oRefRayon.X = m_dRayonX: oRefRayon.Y = m_dRayonY
    oRefRayon.Z = m_dRayonZ: oRefRayon.Altitude = m_dRayonZ
    oRefRayon.Valide = True
End Sub

Attribute VB_Name = "CPointRef"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CPointRef - Point de reference topographique (P1 ou P2)
'
' Contient les donnees geometriques et altimetriques d un point connu.
'
' NOTE VBA : un membre Public de type UDT (Point3d) est interdit dans un
' module de classe (erreur de compilation). Les coordonnees sont donc
' stockees en trois Double ; la conversion vers Point3d se fait par des Sub
' avec parametre de sortie (jamais de retour UDT sur ce poste).
'
' Le parsing du texte est delegue a CInterpolation.
'==============================================================================
Option Explicit

Public X            As Double   ' coordonnees du point (origin du texte)
Public Y            As Double
Public Z            As Double
Public Altitude     As Double   ' altitude numerique
Public Valide       As Boolean  ' True si le point a ete correctement charge

'------------------------------------------------------------------------------
Sub Invalider()
    Valide = False
    Altitude = 0#
End Sub

'------------------------------------------------------------------------------
' Charge la position depuis un Point3d (ex. origin du texte)
Sub DefinirPosition(oPt As Point3d)
    X = oPt.X: Y = oPt.Y: Z = oPt.Z
End Sub

'------------------------------------------------------------------------------
' Copie la position dans le Point3d fourni par l'appelant
Sub CopierPosition(oPt As Point3d)
    oPt.X = X: oPt.Y = Y: oPt.Z = Z
End Sub

Attribute VB_Name = "CSelectBoiteP1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSelectBoiteP1 - Etat 2 : clic explicite sur la cellule Fe de P1
'
' Le snap de P1 est deja memorise dans g_ptSnapP1. Ce clic sert uniquement a
' identifier la cellule regard/grille (parfois plusieurs reseaux proches).
'
'   Data  = cherche la BoiteEP la plus proche du clic dans le rayon
'           g_dTolReseau, memorise ses altitudes et alimente g_oRefFeP1
'           avec (g_ptSnapP1.X, g_ptSnapP1.Y, Fe).
'   Reset = revient au snap P1.
'==============================================================================
Option Explicit

Implements IPrimitiveCommandEvents

Private Sub IPrimitiveCommandEvents_Start()
    ShowCommand "Pente Reseau EU/EP"
    ShowPrompt "Cliquez pres de la cellule regard/grille du P1  (Reset = re-snap P1)"
End Sub

Private Sub IPrimitiveCommandEvents_DataPoint(Point As Point3d, ByVal View As View)
    Dim oInfo As New CBoiteEPInfo
    If Not TrouverBoiteEPProche(Point, TolReseau(), oInfo) Then
        ShowPrompt "Aucune cellule regard/grille (avec Fe:) a moins de " & _
                   TolReseau() & " u.m. - recliquez (cellule P1)"
        Exit Sub
    End If

    g_oBoiteP1.CopierDepuis oInfo
    AlimenterPointRefFeSnap g_oRefFeP1, g_ptSnapP1, g_oBoiteP1
    frmReseauEP.AfficherBoiteP1 g_oBoiteP1

    ShowPrompt "P1 : " & DecrireBoite(g_oBoiteP1) & _
               "  |  snappez le POINT 2"
    CommandState.StartPrimitive New CSnapBoiteP2
End Sub

Private Sub IPrimitiveCommandEvents_Dynamics(Point As Point3d, ByVal View As View, _
                                             ByVal DrawMode As MsdDrawingMode)
End Sub

Private Sub IPrimitiveCommandEvents_Keyin(ByVal Keyin As String)
End Sub

Private Sub IPrimitiveCommandEvents_Reset()
    ShowPrompt "Retour au snap P1 : snappez le POINT 1  (Reset = quitter)"
    CommandState.StartPrimitive New CSnapBoiteP1
End Sub

Private Sub IPrimitiveCommandEvents_Cleanup()
End Sub

Attribute VB_Name = "CSelectBoiteP2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSelectBoiteP2 - Etat 4 : clic explicite sur la cellule Fe de P2
'
' Le snap P2 est deja dans g_ptSnapP2. Ce clic identifie la cellule Fe.
' Si trouve, alimente g_oRefFeP2 et passe a CPlacerPenteReseau. Aucun element
' n'est ajoute au DGN a ce stade : la ligne P1-P2 reste PROVISOIRE (dessinee
' par CPlacerPenteReseau.Dynamics) et disparait au placement pente. Seuls le
' texte pente + fleche seront persistes (via g_oMoteur.CreerPente).
'==============================================================================
Option Explicit

Implements IPrimitiveCommandEvents

Private Sub IPrimitiveCommandEvents_Start()
    ShowCommand "Pente Reseau EU/EP"
    ShowPrompt "P1 : " & DecrireBoite(g_oBoiteP1) & _
               "  |  cliquez pres de la cellule regard/grille du P2"
End Sub

Private Sub IPrimitiveCommandEvents_DataPoint(Point As Point3d, ByVal View As View)
    Dim oInfo As New CBoiteEPInfo
    If Not TrouverBoiteEPProche(Point, TolReseau(), oInfo) Then
        ShowPrompt "Aucune cellule regard/grille (avec Fe:) a moins de " & _
                   TolReseau() & " u.m. - recliquez (cellule P2)"
        Exit Sub
    End If

    g_oBoiteP2.CopierDepuis oInfo
    AlimenterPointRefFeSnap g_oRefFeP2, g_ptSnapP2, g_oBoiteP2

    Dim dDist As Double, dPente As Double
    dDist = Sqr((g_ptSnapP2.X - g_ptSnapP1.X) ^ 2 + (g_ptSnapP2.Y - g_ptSnapP1.Y) ^ 2)
    dPente = g_oCalc.PentePct(g_oRefFeP1, g_oRefFeP2)

    frmReseauEP.AfficherBoiteP2 g_oBoiteP2
    frmReseauEP.AfficherDistancePente dDist, dPente

    ShowPrompt "P2 : " & DecrireBoite(g_oBoiteP2) & _
               "  |  Pente=" & Format$(dPente, "0.0") & _
               "%  ->  cliquez pour placer texte+fleche  (Reset=nouv. selection)"
    CommandState.StartPrimitive New CPlacerPenteReseau
End Sub

Private Sub IPrimitiveCommandEvents_Dynamics(Point As Point3d, ByVal View As View, _
                                             ByVal DrawMode As MsdDrawingMode)
End Sub

Private Sub IPrimitiveCommandEvents_Keyin(ByVal Keyin As String)
End Sub

Private Sub IPrimitiveCommandEvents_Reset()
    ShowPrompt "Retour au snap P2  (Reset = re-clic cellule P1)"
    CommandState.StartPrimitive New CSnapBoiteP2
End Sub

Private Sub IPrimitiveCommandEvents_Cleanup()
End Sub

Attribute VB_Name = "CSelectP1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSelectP1 - Etat commande : selection du point de reference P1
'
' Classe partagee entre les deux commandes via la propriete Mode :
'   modeInterpolation (defaut) : commande Interpolation Topo
'   modePonctuelle             : commande Interpolation Ponctuelle
'==============================================================================
Option Explicit

Implements IPrimitiveCommandEvents

Public Mode As eModeCommande

Private Sub IPrimitiveCommandEvents_Start()
    If Mode = modePonctuelle Then
        ShowCommand "Interpol. Ponctuelle"
    Else
        ShowCommand "Interpolation Topo"
    End If
    ShowPrompt "Cliquez pres du texte altitude du POINT 1  (Reset = quitter)"
End Sub

Private Sub IPrimitiveCommandEvents_DataPoint(Point As Point3d, ByVal View As View)
    ' Cherche le texte/tag/cellule numerique le plus proche du clic
    Dim oText As TextElement
    If Not TrouverAltitudeProche(Point, g_oSettings.dTolTexte, oText) Then
        ShowPrompt "Aucun texte altitude a moins de " & g_oSettings.dTolTexte & _
                   " u.m. - recliquez (P1)"
        Exit Sub
    End If

    ' Parsing de l'altitude
    Dim sSep As String, nDec As Integer
    If Not g_oCalc.LireAltitudeTexte(g_oP1, sSep, nDec) Then
        ShowPrompt "Texte '" & g_oSelectionCourante.ValeurTexte & _
                   "' non numerique - recliquez (P1)"
        Exit Sub
    End If
    g_oSelectionP1.CopierDepuis g_oSelectionCourante

    ' Mise a jour des parametres : texte-modele et format
    If Not oText Is Nothing Then
        g_oSettings.ChargerModeleTexte oText, sSep, nDec
    Else
        g_oSettings.ChargerModeleDepuisTag g_oSelectionCourante.oTag, sSep, nDec
    End If

    ' Mise a jour du formulaire (etat P1 + attributs herites du texte modele)
    If Mode = modePonctuelle Then
        frmInterpolPonct.AfficherP1 g_oP1
        frmInterpolPonct.RafraichirTexte
    Else
        frmInterpolation.AfficherP1 g_oP1
        frmInterpolation.RafraichirTexte
        frmInterpolation.RafraichirPente
    End If

    ShowPrompt "P1 = " & g_oSelectionCourante.ValeurTexte & _
               "  |  Snappez le point terrain P1  (Reset = ancrage du texte)"
    Dim oSuivant As New CSnapP1
    oSuivant.Mode = Mode
    CommandState.StartPrimitive oSuivant
End Sub

Private Sub IPrimitiveCommandEvents_Dynamics(Point As Point3d, ByVal View As View, _
                                             ByVal DrawMode As MsdDrawingMode)
End Sub

Private Sub IPrimitiveCommandEvents_Keyin(ByVal Keyin As String)
End Sub

' Reset au choix de P1 = quitter la commande
Private Sub IPrimitiveCommandEvents_Reset()
    If Mode = modePonctuelle Then
        frmInterpolPonct.Hide
        ShowPrompt "Interpol. Ponctuelle : termine."
    Else
        frmInterpolation.Hide
        ShowPrompt "Interpolation Topo : termine."
    End If
    CommandState.StartDefaultCommand
End Sub

Private Sub IPrimitiveCommandEvents_Cleanup()
End Sub

Attribute VB_Name = "CSelectP2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSelectP2 - Etat commande : selection du point de reference P2
'
' Classe partagee entre les deux commandes via la propriete Mode :
'   modeInterpolation : P2 obligatoire, Reset = revenir a P1
'   modePonctuelle    : P2 optionnel, Reset = pente manuelle, demarrer le chemin
'==============================================================================
Option Explicit

Implements IPrimitiveCommandEvents

Public Mode As eModeCommande

Private Sub IPrimitiveCommandEvents_Start()
    If Mode = modePonctuelle Then
        ShowCommand "Interpol. Ponctuelle"
        ShowPrompt "P2 optionnel : Data=selectionner P2  Reset=pente manuelle, demarrer le chemin"
    Else
        ShowCommand "Interpolation Topo"
        ShowPrompt "Cliquez pres du texte altitude du POINT 2"
    End If
End Sub

Private Sub IPrimitiveCommandEvents_DataPoint(Point As Point3d, ByVal View As View)
    Dim oText As TextElement
    If Not TrouverAltitudeProche(Point, g_oSettings.dTolTexte, oText) Then
        ShowPrompt "Aucun texte altitude a moins de " & g_oSettings.dTolTexte & _
                   " u.m. - recliquez (P2)"
        Exit Sub
    End If

    Dim sSep As String, nDec As Integer
    If Not g_oCalc.LireAltitudeTexte(g_oP2, sSep, nDec) Then
        ShowPrompt "Texte '" & g_oSelectionCourante.ValeurTexte & _
                   "' non numerique - recliquez (P2)"
        Exit Sub
    End If
    g_oSelectionP2.CopierDepuis g_oSelectionCourante

    If Mode = modePonctuelle Then
        frmInterpolPonct.AfficherP2 g_oP2
    Else
        g_oSettings.AjusterDecimales nDec
        frmInterpolation.AfficherP2 g_oP2
    End If

    ShowPrompt "P2 = " & g_oSelectionCourante.ValeurTexte & _
               "  |  Snappez le point terrain P2  (Reset = ancrage du texte)"
    Dim oSuivant As New CSnapP2
    oSuivant.Mode = Mode
    CommandState.StartPrimitive oSuivant
End Sub

Private Sub IPrimitiveCommandEvents_Dynamics(Point As Point3d, ByVal View As View, _
                                             ByVal DrawMode As MsdDrawingMode)
End Sub

Private Sub IPrimitiveCommandEvents_Keyin(ByVal Keyin As String)
End Sub

' Reset pendant P2 :
'   Interpolation = revenir a P1
'   Ponctuelle    = sauter P2, demarrer le chemin avec la pente manuelle
Private Sub IPrimitiveCommandEvents_Reset()
    If Mode = modePonctuelle Then
        ShowPrompt "Pente manuelle  ->  CHEMIN : Data=placer un point  Reset=nouv. selection"
        CommandState.StartPrimitive New CPlacerPonctuel
    Else
        frmInterpolation.ReinitialiserEtat
        ShowPrompt "Retour au POINT 1 : cliquez pres du texte altitude  (Reset = quitter)"
        CommandState.StartPrimitive New CSelectP1
    End If
End Sub

Private Sub IPrimitiveCommandEvents_Cleanup()
End Sub

Attribute VB_Name = "CSnapBoiteP1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSnapBoiteP1 - Etat 1 : snap du POINT 1 (axe tampon/grille)
'
'   Data  = memorise la position snappee dans g_ptSnapP1 -> passe au clic cellule.
'   Reset = quitte la commande.
'==============================================================================
Option Explicit

Implements IPrimitiveCommandEvents

Private Sub IPrimitiveCommandEvents_Start()
    ShowCommand "Pente Reseau EU/EP"
    frmReseauEP.ReinitialiserEtat
    ShowPrompt "Snappez le POINT 1 (axe tampon/grille)  (Reset = quitter)"
End Sub

Private Sub IPrimitiveCommandEvents_DataPoint(Point As Point3d, ByVal View As View)
    g_ptSnapP1 = Point
    ShowPrompt "P1 snappe  ->  cliquez pres de la cellule regard/grille du P1"
    CommandState.StartPrimitive New CSelectBoiteP1
End Sub

Private Sub IPrimitiveCommandEvents_Dynamics(Point As Point3d, ByVal View As View, _
                                             ByVal DrawMode As MsdDrawingMode)
End Sub

Private Sub IPrimitiveCommandEvents_Keyin(ByVal Keyin As String)
End Sub

Private Sub IPrimitiveCommandEvents_Reset()
    frmReseauEP.Hide
    ShowPrompt "Pente Reseau EU/EP : termine."
    CommandState.StartDefaultCommand
End Sub

Private Sub IPrimitiveCommandEvents_Cleanup()
End Sub

Attribute VB_Name = "CSnapBoiteP2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSnapBoiteP2 - Etat 3 : snap du POINT 2
'
'   Dynamics = ligne provisoire g_ptSnapP1 -> curseur
'   Data     = memorise g_ptSnapP2 (verif P1 <> P2) -> passe au clic cellule P2
'   Reset    = revient au clic cellule P1
'==============================================================================
Option Explicit

Implements IPrimitiveCommandEvents

Private Sub IPrimitiveCommandEvents_Start()
    ShowCommand "Pente Reseau EU/EP"
    ShowPrompt "P1 : " & DecrireBoite(g_oBoiteP1) & _
               "  |  snappez le POINT 2"
    CommandState.StartDynamics
End Sub

Private Sub IPrimitiveCommandEvents_Dynamics(Point As Point3d, ByVal View As View, _
                                             ByVal DrawMode As MsdDrawingMode)
    ' On force msdDrawingModeTemporary : sinon MicroStation peut recevoir un
    ' DrawMode Normal et laisser la derniere frame dessinee dans le DGN a la
    ' transition vers l'etat suivant.
    On Error Resume Next
    Dim ptA As Point3d
    ptA = g_ptSnapP1
    ptA.Z = Point.Z   ' vue a plat pour lisibilite pendant le drag

    Dim oL As LineElement
    Set oL = CreateLineElement2(Nothing, ptA, Point)
    oL.Color = 3
    oL.Redraw msdDrawingModeTemporary
    On Error GoTo 0
End Sub

Private Sub IPrimitiveCommandEvents_DataPoint(Point As Point3d, ByVal View As View)
    Dim dD As Double
    dD = Sqr((Point.X - g_ptSnapP1.X) ^ 2 + (Point.Y - g_ptSnapP1.Y) ^ 2)
    If dD < 0.001 Then
        ShowPrompt "P2 confondu avec P1 - resnappez un autre POINT 2"
        Exit Sub
    End If

    g_ptSnapP2 = Point
    ShowPrompt "P2 snappe  ->  cliquez pres de la cellule regard/grille du P2"
    CommandState.StartPrimitive New CSelectBoiteP2
End Sub

Private Sub IPrimitiveCommandEvents_Keyin(ByVal Keyin As String)
End Sub

Private Sub IPrimitiveCommandEvents_Reset()
    ShowPrompt "Retour au clic cellule P1  (Reset = re-snap P1)"
    CommandState.StartPrimitive New CSelectBoiteP1
End Sub

Private Sub IPrimitiveCommandEvents_Cleanup()
End Sub

Attribute VB_Name = "CSnapP1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSnapP1 - Etat commande : positionnement optionnel du point terrain pour P1
'
' Apres selection du texte altitude (CSelectP1), l'utilisateur peut :
'   Data  = snapper/cliquer le point terrain reel (remplace l'ancrage du texte)
'   Reset = garder le point d'ancrage du texte comme position terrain
'
' Classe partagee entre les deux commandes via la propriete Mode.
'==============================================================================
Option Explicit

Implements IPrimitiveCommandEvents

Public Mode As eModeCommande

Private Sub IPrimitiveCommandEvents_Start()
    If Mode = modePonctuelle Then
        ShowCommand "Interpol. Ponctuelle"
    Else
        ShowCommand "Interpolation Topo"
    End If
    ShowPrompt "P1 = " & g_oSelectionCourante.ValeurTexte & _
               "  |  Snappez le point terrain P1  (Reset = ancrage du texte)"
End Sub

Private Sub IPrimitiveCommandEvents_DataPoint(Point As Point3d, ByVal View As View)
    g_oP1.DefinirPosition Point

    If Mode = modePonctuelle Then
        frmInterpolPonct.AfficherP1 g_oP1
        ShowPrompt "P1 positionne  ->  P2 optionnel (Data=selectionner P2  Reset=pente manuelle)"
    Else
        frmInterpolation.AfficherP1 g_oP1
        ShowPrompt "P1 positionne  ->  cliquez pres du texte altitude du POINT 2"
    End If

    PasserSelectionP2
End Sub

Private Sub IPrimitiveCommandEvents_Dynamics(Point As Point3d, ByVal View As View, _
                                             ByVal DrawMode As MsdDrawingMode)
End Sub

Private Sub IPrimitiveCommandEvents_Keyin(ByVal Keyin As String)
End Sub

' Reset = garder l'ancrage du texte et passer a P2
Private Sub IPrimitiveCommandEvents_Reset()
    If Mode = modePonctuelle Then
        ShowPrompt "P1 = ancrage texte  ->  P2 optionnel (Data=selectionner P2  Reset=pente manuelle)"
    Else
        ShowPrompt "P1 = ancrage texte  ->  cliquez pres du texte altitude du POINT 2"
    End If

    PasserSelectionP2
End Sub

Private Sub IPrimitiveCommandEvents_Cleanup()
End Sub

'------------------------------------------------------------------------------
Private Sub PasserSelectionP2()
    Dim oSuivant As New CSelectP2
    oSuivant.Mode = Mode
    CommandState.StartPrimitive oSuivant
End Sub

Attribute VB_Name = "CSnapP2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSnapP2 - Etat commande : positionnement optionnel du point terrain pour P2
'
' Apres selection du texte altitude (CSelectP2), l'utilisateur peut :
'   Data  = snapper/cliquer le point terrain reel (remplace l'ancrage du texte)
'   Reset = garder le point d'ancrage du texte comme position terrain
'
' Classe partagee entre les deux commandes via la propriete Mode :
'   modeInterpolation : passe au placement du point interpole (CPlacerPoint)
'   modePonctuelle    : calcule la pente P1-P2, la reporte dans les parametres
'                       chemin, puis demarre le chemin (CPlacerPonctuel)
'==============================================================================
Option Explicit

Implements IPrimitiveCommandEvents

Public Mode As eModeCommande

Private Sub IPrimitiveCommandEvents_Start()
    If Mode = modePonctuelle Then
        ShowCommand "Interpol. Ponctuelle"
    Else
        ShowCommand "Interpolation Topo"
    End If
    ShowPrompt "P2 = " & g_oSelectionCourante.ValeurTexte & _
               "  |  Snappez le point terrain P2  (Reset = ancrage du texte)"
End Sub

Private Sub IPrimitiveCommandEvents_DataPoint(Point As Point3d, ByVal View As View)
    g_oP2.DefinirPosition Point

    If g_oCalc.Dist2DRef(g_oP1, g_oP2) < 0.001 Then
        ShowPrompt "P1 et P2 confondus - snappez un autre point terrain (P2)"
        Exit Sub
    End If

    If Mode = modePonctuelle Then
        DemarrerPlacement ""
    Else
        DemarrerPlacement "P2 positionne  |  "
    End If
End Sub

Private Sub IPrimitiveCommandEvents_Dynamics(Point As Point3d, ByVal View As View, _
                                             ByVal DrawMode As MsdDrawingMode)
End Sub

Private Sub IPrimitiveCommandEvents_Keyin(ByVal Keyin As String)
End Sub

' Reset = garder l'ancrage du texte et passer au placement
Private Sub IPrimitiveCommandEvents_Reset()
    If g_oCalc.Dist2DRef(g_oP1, g_oP2) < 0.001 Then
        ShowPrompt "P1 et P2 confondus - choisissez un autre texte (P2)"
        Dim oRetour As New CSelectP2
        oRetour.Mode = Mode
        CommandState.StartPrimitive oRetour
        Exit Sub
    End If

    If Mode = modePonctuelle Then
        DemarrerPlacement "P2 = ancrage texte  "
    Else
        DemarrerPlacement "P2 = ancrage texte  |  "
    End If
End Sub

Private Sub IPrimitiveCommandEvents_Cleanup()
End Sub

'------------------------------------------------------------------------------
' Segment P1-P2 valide : met a jour le formulaire et lance l'etat de placement
' selon le mode. sPrefixe complete le message d'invite (origine du point P2).
Private Sub DemarrerPlacement(sPrefixe As String)
    If Mode = modePonctuelle Then
        AppliquerPenteP1P2
        frmInterpolPonct.AfficherP2 g_oP2
        frmInterpolPonct.RafraichirChemin
        ShowPrompt sPrefixe & "Pente=" & Format$(g_oSettings.oChemin.Pente, "0.0") & _
                   "%  ->  CHEMIN : Data=placer un point  Reset=nouv. selection"
        CommandState.StartPrimitive New CPlacerPonctuel
    Else
        frmInterpolation.AfficherP2 g_oP2
        frmInterpolation.AfficherSegment g_oCalc.InfoSegment(g_oP1, g_oP2)
        frmInterpolation.ActiverBoutonsActions True
        ShowPrompt sPrefixe & g_oCalc.InfoSegment(g_oP1, g_oP2) & _
                   "  ->  deplacez le curseur. Data=figer altitude  Reset=nouv. selection"
        CommandState.StartPrimitive New CPlacerPoint
    End If
End Sub

'------------------------------------------------------------------------------
Private Sub AppliquerPenteP1P2()
    Dim dPente As Double
    dPente = g_oCalc.PentePct(g_oP1, g_oP2)
    g_oSettings.oChemin.Pente = dPente
    g_oSettings.oChemin.PenteActive = True
End Sub

Attribute VB_Name = "CSymboCercle"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSymboCercle - Attributs de symbologie du cercle topo
'
' Configures par l'utilisateur via frmInterpolation (Tool Settings).
' Persistent pendant toute la duree de la commande.
'==============================================================================
Option Explicit

Public Rayon        As Double   ' demi-diametre en unites maitre
Public Couleur      As Long     ' index couleur MicroStation 0-255
Public NomNiveau    As String   ' "" = meme niveau que le texte P1

'------------------------------------------------------------------------------
' Valeurs par defaut au demarrage de la commande
Sub InitDefauts()
    Rayon = 0.05    ' diametre = 0.10
    Couleur = 2     ' vert
    NomNiveau = ""  ' niveau du texte P1
End Sub

'------------------------------------------------------------------------------
' Diametre (propriete calculee pour l'affichage dans le formulaire)
Property Get Diametre() As Double
    Diametre = Rayon * 2#
End Property

Property Let Diametre(dDiam As Double)
    Rayon = dDiam / 2#
End Property

Attribute VB_Name = "CSymboPente"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSymboPente - Attributs de l'indicateur de pente (texte + fleche)
'
' Meme role que CSymboTexte / CSymboCercle : simple sac de proprietes,
' sans dependance a l'API MicroStation.
' Hauteur / Largeur / Couleur sont recalees sur le texte-modele P1 par
' CMstSettings.ChargerModeleTexte, sauf si Perso est actif.
'==============================================================================
Option Explicit

Public Perso            As Boolean   ' True = parametres personnalises (sinon herites de P1)
Public Hauteur          As Double    ' hauteur du texte pente
Public Largeur          As Double    ' largeur du texte pente
Public Couleur          As Long      ' couleur du texte pente (index 0-255)
Public NomNiveau        As String    ' niveau du texte pente ("" = niveau actif)
Public FlecheLongueur   As Double    ' longueur de la fleche (u.m.)
Public FlecheCouleur    As Long      ' couleur de la fleche (index 0-255)
Public Decimales        As Integer   ' decimales du texte pente (defaut 1)

'------------------------------------------------------------------------------
Sub InitDefauts()
    Perso = False
    Hauteur = 0.1
    Largeur = 0.1
    Couleur = 0
    NomNiveau = ""
    FlecheLongueur = 1#
    FlecheCouleur = 3
    Decimales = 1
End Sub

Attribute VB_Name = "CSymboTexte"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'==============================================================================
' CSymboTexte - Attributs de symbologie du texte altitude
'
' CommeModele = True (defaut) : le texte cree reprend tous les attributs du
' texte P1 (via CreateTextElement1 avec modele) ; NomNiveau/Couleur refletent
' alors le modele, a titre informatif.
' CommeModele = False : NomNiveau/Couleur sont choisis par l'utilisateur dans
' le formulaire et appliques au texte cree (NomNiveau vide = niveau du P1).
'
' Stocke egalement la convention de formatage numerique (separateur, decimales)
' deduite du texte source.
'==============================================================================
Option Explicit

Public CommeModele  As Boolean  ' True = memes attributs que le texte P1
Public NomNiveau    As String   ' niveau du texte cree (nom ou numero)
Public Couleur      As Long     ' index couleur MicroStation 0-255

Public SepDecimal   As String   ' "." ou "," : separateur lu sur le texte source
Public Decimales    As Integer  ' nombre de decimales (max de P1 et P2)

'------------------------------------------------------------------------------
Private Sub Class_Initialize()
    CommeModele = True
End Sub

'------------------------------------------------------------------------------
' Charge NomNiveau et Couleur depuis le TextElement P1 - uniquement en mode
' modele, pour ne pas ecraser un choix utilisateur.
' SepDecimal et Decimales sont renseignes par CInterpolation lors du parsing.
Sub ChargerDepuisElement(oText As TextElement)
    If Not CommeModele Then Exit Sub
    On Error Resume Next
    NomNiveau = oText.Level.Name
    Couleur = oText.Color
    On Error GoTo 0
End Sub

Attribute VB_Name = "InterpolPonctuelle"
'==============================================================================
' InterpolPonctuelle - Point d'entree de la commande Interpolation Ponctuelle
'
' L'initialisation commune (globals, formulaire) est dans
' InterpolationTopoV2.bas.
'
' LANCEMENT :
'   key-in : vba run [InterpolationTopoV2]InterpolPonctuelle
'==============================================================================
Option Explicit

'------------------------------------------------------------------------------
Sub InterpolPonctuelle()
    If Not EnvironnementPret("Interpol. Ponctuelle") Then Exit Sub
    InitialiserContexte
    AfficherFormulaire frmInterpolPonct

    Dim oEtat As New CSelectP1
    oEtat.Mode = modePonctuelle
    CommandState.StartPrimitive oEtat
End Sub

Attribute VB_Name = "InterpolationTopoV2"
'==============================================================================
' InterpolationTopoV2 - Module principal - MicroStation V8i SS3 (VBA)
'
' Interpole l'altitude d'un point situe sur la droite reliant deux textes
' d'altitude existants, avec apercu dynamique, puis cree :
'   - un texte altitude (memes proprietes que le texte P1, pris comme modele)
'   - un cercle centre sur le point projete
'
' Architecture V2 : classes a responsabilites separees + formulaire modeless
'
' Ce module ne contient que les globals partages, l'initialisation commune et
' le point d'entree de la commande Interpolation. La recherche des altitudes
' sources est dans RechercheAltitude.bas ; le point d'entree de la commande
' Interpolation Ponctuelle est dans InterpolPonctuelle.bas.
'
' LANCEMENT :
'   key-in : vba run [InterpolationTopoV2]InterpolerPoint
'==============================================================================
Option Explicit

' --- Mode de commande ---
' Les classes d'etat (CSelectP1/P2, CSnapP1/P2) sont partagees entre les deux
' commandes : leur propriete Mode choisit formulaire, invites et etat suivant.
' modeInterpolation = 0 : valeur par defaut d'une instance creee sans Mode.
Public Enum eModeCommande
    modeInterpolation = 0
    modePonctuelle = 1
End Enum

' --- Instances partagees entre les classes de commande ---
' Chaque classe recoit ces references mais ne les cree pas.
Public g_oSettings  As CMstSettings      ' parametres (symbologie, tolerance)
Public g_oP1        As CPointRef         ' point de reference 1
Public g_oP2        As CPointRef         ' point de reference 2
Public g_oCalc      As CInterpolation    ' moteur de calcul pur
Public g_oMoteur    As CMoteurGraphique  ' moteur de creation graphique
Public g_oSelectionCourante As CAltitudeSelection ' dernier texte/tag/cellule trouve
Public g_oSelectionP1       As CAltitudeSelection ' source modele de creation
Public g_oSelectionP2       As CAltitudeSelection ' source altitude P2

'------------------------------------------------------------------------------
' Point d'entree de la commande Interpolation
Sub InterpolerPoint()
    If Not EnvironnementPret("Interpolation Topo") Then Exit Sub
    InitialiserContexte
    AfficherFormulaire frmInterpolation

    Dim oEtat As New CSelectP1
    oEtat.Mode = modeInterpolation
    CommandState.StartPrimitive oEtat
End Sub

'==============================================================================
' Initialisation commune aux deux commandes
'==============================================================================

'------------------------------------------------------------------------------
' Verifie qu'un fichier DGN est ouvert. Affiche un message sinon.
Public Function EnvironnementPret(sTitre As String) As Boolean
    Dim oDgn As DesignFile
    On Error Resume Next
    Set oDgn = ActiveDesignFile
    On Error GoTo 0
    If oDgn Is Nothing Then
        MsgBox "Ouvrez d'abord un fichier DGN.", vbExclamation, sTitre
        EnvironnementPret = False
    Else
        EnvironnementPret = True
    End If
End Function

'------------------------------------------------------------------------------
' Instanciation unique des objets partages par les classes de commande.
Public Sub InitialiserContexte()
    Set g_oSettings = New CMstSettings
    g_oSettings.Init

    Set g_oP1 = New CPointRef
    Set g_oP2 = New CPointRef
    Set g_oCalc = New CInterpolation
    Set g_oMoteur = New CMoteurGraphique
    Set g_oSelectionCourante = New CAltitudeSelection
    Set g_oSelectionP1 = New CAltitudeSelection
    Set g_oSelectionP2 = New CAltitudeSelection
End Sub

'------------------------------------------------------------------------------
' Initialise, positionne et affiche un formulaire modeless (Tool Settings).
' oFrm en Object : accepte frmInterpolation comme frmInterpolPonct.
Public Sub AfficherFormulaire(oFrm As Object)
    oFrm.Initialiser g_oSettings
    oFrm.StartUpPosition = 0
    oFrm.Left = Application.Width * 0.6
    oFrm.Top = Application.Height * 0.05
    oFrm.Show vbModeless
End Sub

Attribute VB_Name = "RechercheAltitude"
'==============================================================================
' RechercheAltitude - Moteur de recherche des altitudes sources
'
' Detecte le texte, tag ou cellule numerique le plus proche d'un clic, dans le
' modele actif et dans les references attachees (coordonnees converties dans le
' repere du modele actif). Le resultat complet est memorise dans
' g_oSelectionCourante (voir InterpolationTopoV2.bas pour les globals).
'
' Fonctions publiques :
'   TrouverAltitudeProche : point d'entree utilise par les classes de commande
'   TrouverTexteProche    : variante renvoyant le TextElement source
'==============================================================================
Option Explicit

'------------------------------------------------------------------------------
' Cherche l'altitude la plus proche (texte, cellule ou tag).
' Renvoie True si trouvee. Le resultat complet est dans g_oSelectionCourante,
' et oTextOut recoit le TextElement source (Nothing si c'est un tag).
Function TrouverAltitudeProche(oPt As Point3d, dRayon As Double, _
                                oTextOut As TextElement) As Boolean
    Set oTextOut = TrouverTexteProche(oPt, dRayon)
    TrouverAltitudeProche = g_oSelectionCourante.Trouvee
End Function

'------------------------------------------------------------------------------
' Cherche le texte numerique le plus proche du clic dans le rayon donne.
Function TrouverTexteProche(oPt As Point3d, dRayon As Double) As TextElement
    Set TrouverTexteProche = Nothing

    Dim oScan As New ElementScanCriteria
    oScan.ExcludeAllTypes
    oScan.IncludeType msdElementTypeText
    oScan.IncludeType msdElementTypeCellHeader
    oScan.IncludeType msdElementTypeTag

    Dim dMinDist As Double: dMinDist = dRayon
    Dim oBest As CAltitudeSelection
    Set oBest = New CAltitudeSelection

    ScannerAltitudeDansModele ActiveModelReference, Nothing, oScan, oPt, dMinDist, oBest

    Dim oAttachments As Object
    Set oAttachments = Nothing
    On Error Resume Next
    Set oAttachments = ActiveModelReference.Attachments
    On Error GoTo 0

    Dim nCount As Long: nCount = 0
    On Error Resume Next
    If Not oAttachments Is Nothing Then nCount = oAttachments.Count
    On Error GoTo 0

    Dim i As Long
    For i = 1 To nCount
        Dim oAtt As Object
        Set oAtt = Nothing
        On Error Resume Next
        Set oAtt = oAttachments(i)
        On Error GoTo 0
        If Not oAtt Is Nothing Then
            If AttachmentAffiche(oAtt) Then
                ScannerAltitudeDansModele oAtt, oAtt, oScan, oPt, dMinDist, oBest
            End If
        End If
    Next i

    If g_oSelectionCourante Is Nothing Then Set g_oSelectionCourante = New CAltitudeSelection
    g_oSelectionCourante.CopierDepuis oBest
    Set TrouverTexteProche = oBest.oTexte
End Function

'------------------------------------------------------------------------------
' Scanne un modele ou une reference attachee. Les points stockes dans oBest sont
' toujours exprimes dans le repere du modele actif.
Private Sub ScannerAltitudeDansModele(oModel As Object, oAttachment As Object, _
        oScan As ElementScanCriteria, oPtClic As Point3d, _
        dMinDist As Double, oBest As CAltitudeSelection)

    Dim oEnum As ElementEnumerator
    On Error Resume Next
    Set oEnum = oModel.Scan(oScan)
    If Err.Number <> 0 Or oEnum Is Nothing Then
        Err.Clear
        On Error GoTo 0
        Exit Sub
    End If
    On Error GoTo 0

    Do While oEnum.MoveNext
        Dim oElem As Element
        Set oElem = oEnum.Current

        If EstSurNiveauGele(oElem) Then GoTo SuivantElem

        If oElem.Type = msdElementTypeTag Then
            TraiterTagCandidate oElem, oAttachment, oPtClic, dMinDist, oBest

        ElseIf oElem.IsTextElement Then
            TraiterTexteCandidate oElem, oAttachment, oPtClic, dMinDist, oBest

        ElseIf oElem.Type = msdElementTypeCellHeader Then
            TraiterCelluleCandidate oElem, oAttachment, oPtClic, dMinDist, oBest
        End If
SuivantElem:
    Loop
End Sub

'------------------------------------------------------------------------------
Private Sub TraiterTagCandidate(oElem As Element, oAttachment As Object, _
        oPtClic As Point3d, dMinDist As Double, oBest As CAltitudeSelection)

    Dim oTag As TagElement
    Set oTag = oElem

    Dim sTagVal As String
    sTagVal = Trim$(CStr(oTag.Value))
    If Not g_oCalc.EstNombre(Replace(sTagVal, ",", ".")) Then Exit Sub

    Dim ptMaster As Point3d
    TransformerPointVersMaitre oAttachment, oTag.Origin, ptMaster

    Dim dD As Double
    dD = g_oCalc.Dist2D(oPtClic, ptMaster)
    If dD >= dMinDist Then Exit Sub

    dMinDist = dD
    oBest.Vider
    oBest.ValeurTexte = sTagVal
    oBest.DefinirOrigine ptMaster
    oBest.EstReference = Not (oAttachment Is Nothing)
    Set oBest.oAttachment = oAttachment

    Dim oBase As Element
    Set oBase = Nothing
    On Error Resume Next
    Set oBase = oTag.BaseElement
    On Error GoTo 0

    If Not oBase Is Nothing Then
        If oBase.Type = msdElementTypeCellHeader Then
            Set oBest.oCellule = oBase
            oBest.TagDefName = oTag.TagDefinitionName
            Exit Sub
        End If
    End If

    Set oBest.oTag = oTag
End Sub

'------------------------------------------------------------------------------
Private Sub TraiterTexteCandidate(oElem As Element, oAttachment As Object, _
        oPtClic As Point3d, dMinDist As Double, oBest As CAltitudeSelection)

    Dim oTxt As TextElement
    Set oTxt = oElem

    Dim sTxtVal As String
    sTxtVal = Trim$(oTxt.Text)
    If Not g_oCalc.EstNombre(Replace(sTxtVal, ",", ".")) Then Exit Sub

    Dim ptMaster As Point3d
    TransformerPointVersMaitre oAttachment, oTxt.Origin, ptMaster

    Dim dD As Double
    dD = g_oCalc.Dist2D(oPtClic, ptMaster)
    If dD >= dMinDist Then Exit Sub

    dMinDist = dD
    oBest.Vider
    oBest.ValeurTexte = sTxtVal
    oBest.DefinirOrigine ptMaster
    oBest.EstReference = Not (oAttachment Is Nothing)
    Set oBest.oAttachment = oAttachment
    Set oBest.oTexte = oTxt
End Sub

'------------------------------------------------------------------------------
Private Sub TraiterCelluleCandidate(oElem As Element, oAttachment As Object, _
        oPtClic As Point3d, dMinDist As Double, oBest As CAltitudeSelection)

    Dim oCell As CellElement
    Set oCell = oElem

    Dim sCellVal As String
    Dim sCellTagDef As String
    Dim oTxtCell As TextElement
    Dim ptOrigineAltitude As Point3d
    If Not ExtraireAltitudeDeCellule(oCell, sCellVal, sCellTagDef, _
                                     oTxtCell, ptOrigineAltitude) Then Exit Sub

    Dim ptMaster As Point3d
    TransformerPointVersMaitre oAttachment, ptOrigineAltitude, ptMaster

    Dim dD As Double
    dD = g_oCalc.Dist2D(oPtClic, ptMaster)
    If dD >= dMinDist Then Exit Sub

    dMinDist = dD
    oBest.Vider
    oBest.ValeurTexte = sCellVal
    oBest.TagDefName = sCellTagDef
    oBest.DefinirOrigine ptMaster
    oBest.EstReference = Not (oAttachment Is Nothing)
    Set oBest.oAttachment = oAttachment
    Set oBest.oCellule = oCell
    Set oBest.oTexte = oTxtCell
End Sub

'------------------------------------------------------------------------------
Private Function AttachmentAffiche(oAttachment As Object) As Boolean
    AttachmentAffiche = True
    On Error Resume Next
    AttachmentAffiche = CBool(oAttachment.IsDisplayed)
    If Err.Number <> 0 Then
        Err.Clear
        AttachmentAffiche = True
    End If
    On Error GoTo 0
End Function

'------------------------------------------------------------------------------
' Convertit un point issu d'une reference vers le repere du modele actif.
' MicroStation renvoie les coordonnees scannees dans un espace DEJA compatible
' avec le master. Le ScaleFactor de l'attachement est une echelle graphique du
' CONTENU (taille visuelle), pas des positions : l'appliquer decale et dilate
' tout. On applique uniquement la translation MasterOrigin - ReferenceOrigin.
Private Sub TransformerPointVersMaitre(oAttachment As Object, _
        oPtSource As Point3d, oPtMaster As Point3d)

    oPtMaster = oPtSource
    If oAttachment Is Nothing Then Exit Sub

    Dim ptRefOrigin As Point3d
    Dim ptMasterOrigin As Point3d

    ptRefOrigin.X = 0#: ptRefOrigin.Y = 0#: ptRefOrigin.Z = 0#
    ptMasterOrigin.X = 0#: ptMasterOrigin.Y = 0#: ptMasterOrigin.Z = 0#

    On Error Resume Next
    ptRefOrigin = oAttachment.ReferenceOrigin
    If Err.Number <> 0 Then
        Err.Clear
        ptRefOrigin.X = 0#: ptRefOrigin.Y = 0#: ptRefOrigin.Z = 0#
    End If

    ptMasterOrigin = oAttachment.MasterOrigin
    If Err.Number <> 0 Then
        Err.Clear
        ptMasterOrigin.X = 0#: ptMasterOrigin.Y = 0#: ptMasterOrigin.Z = 0#
    End If
    On Error GoTo 0

    oPtMaster.X = ptMasterOrigin.X + (oPtSource.X - ptRefOrigin.X)
    oPtMaster.Y = ptMasterOrigin.Y + (oPtSource.Y - ptRefOrigin.Y)
    oPtMaster.Z = ptMasterOrigin.Z + (oPtSource.Z - ptRefOrigin.Z)
End Sub

'------------------------------------------------------------------------------
' Teste si l'element est sur un niveau gele. Renvoie False en cas d'erreur
' (element sans niveau valide) pour ne pas bloquer le scan.
Private Function EstSurNiveauGele(oElem As Element) As Boolean
    On Error GoTo Securite
    Dim oLvl As Level
    Set oLvl = oElem.Level
    EstSurNiveauGele = Not oLvl.IsDisplayedInView(ActiveDesignFile.Views(1))
    Exit Function
Securite:
    EstSurNiveauGele = False
End Function

'------------------------------------------------------------------------------
' Parcourt les sous-elements d'une cellule et cherche une altitude numerique.
' Cherche d'abord un tag, puis un texte. Renvoie la valeur trouvee dans sVal,
' le nom de definition du tag dans sDefName (vide si c'est un texte),
' et le TextElement si c'est un texte (Nothing si c'est un tag).
Private Function ExtraireAltitudeDeCellule(oCell As CellElement, _
        sVal As String, sDefName As String, oTxtOut As TextElement, _
        ptOrigineOut As Point3d) As Boolean
    ExtraireAltitudeDeCellule = False
    sDefName = ""
    Set oTxtOut = Nothing
    ptOrigineOut = oCell.Origin

    Dim oSubEnum As ElementEnumerator
    Set oSubEnum = oCell.GetSubElements
    Do While oSubEnum.MoveNext
        If EstSurNiveauGele(oSubEnum.Current) Then GoTo SuivantSub

        ' Chercher un tag numerique
        If oSubEnum.Current.Type = msdElementTypeTag Then
            Dim oTag As TagElement
            Set oTag = oSubEnum.Current
            Dim sTV As String
            sTV = Trim$(CStr(oTag.Value))
            If g_oCalc.EstNombre(Replace(sTV, ",", ".")) Then
                sVal = sTV
                sDefName = oTag.TagDefinitionName
                ptOrigineOut = oTag.Origin
                ExtraireAltitudeDeCellule = True
                Exit Function
            End If
        End If

        ' Chercher un texte numerique
        If oSubEnum.Current.IsTextElement Then
            Dim oT As TextElement
            Set oT = oSubEnum.Current
            If g_oCalc.EstNombre(Replace(Trim$(oT.Text), ",", ".")) Then
                sVal = Trim$(oT.Text)
                Set oTxtOut = oT
                ptOrigineOut = oT.Origin
                ExtraireAltitudeDeCellule = True
                Exit Function
            End If
        End If
SuivantSub:
    Loop
End Function

Attribute VB_Name = "ReseauEP"
'==============================================================================
' ReseauEP - Module reseau EU/EP : pente entre deux regards/grilles
'
' Flux en 4 clics + 1 (5 etapes) :
'   1) CSnapBoiteP1   : snap sur l'axe P1 (tampon/grille)  -> g_ptSnapP1
'   2) CSelectBoiteP1 : clic pres de la cellule qui donne le Fe de P1
'                       -> g_oBoiteP1 (T:/Fe:/Prof:), g_oRefFeP1 = (P1 snap, Fe)
'   3) CSnapBoiteP2   : snap sur l'axe P2 (dynamics : ligne P1_snap -> curseur)
'                       -> g_ptSnapP2
'   4) CSelectBoiteP2 : clic pres de la cellule Fe de P2
'                       -> ligne definitive P1_snap -> P2_snap au niveau Fe
'   5) CPlacerPenteReseau : texte pente + fleche (comme V2 PlacerPente)
'
' Le point du trace et du calcul est le point SNAPPE, pas l'origine de la
' cellule (des reseaux proches peuvent rendre la cellule la plus proche
' ambigue : le clic explicite sur la cellule leve l'ambiguite).
'
' Le module s'appuie sur g_oCalc/g_oMoteur/g_oSettings deja fournis par
' InterpolationTopoV2 (fonction InitialiserContexte) : on ne duplique ni le
' calcul de pente ni le rendu de la fleche. On complete avec g_oBoiteP1/P2
' (donnees reseau) et deux CPointRef alimentes par les Fe pour reutiliser
' g_oMoteur.CreerPente / DessinPenteDynamique.
'
' LANCEMENT :
'   key-in : vba run [InterpolationTopoV2]PenteReseauEP
'==============================================================================
Option Explicit

' --- Instances partagees entre les classes de commande reseau ---
Public g_oBoiteP1        As CBoiteEPInfo
Public g_oBoiteP2        As CBoiteEPInfo
Public g_oParserBoite    As CBoiteEPParser
Public g_oRefFeP1        As CPointRef   ' alimente avec (snap XY, Fe) pour g_oMoteur
Public g_oRefFeP2        As CPointRef
Public g_dTolReseau      As Double      ' rayon de recherche autour du clic (u.m.),
                                        ' modifiable via frmReseauEP

' --- Points snappes (positions exactes cliquees, servent au trace) ---
' Publics dans un .bas : les UDT Point3d sont autorises hors modules de classe.
Public g_ptSnapP1        As Point3d
Public g_ptSnapP2        As Point3d

'------------------------------------------------------------------------------
' Point d'entree de la commande Pente Reseau EU/EP
Sub PenteReseauEP()
    If Not EnvironnementPret("Pente Reseau EU/EP") Then Exit Sub

    ' Contexte commun (fournit g_oSettings/g_oCalc/g_oMoteur)
    InitialiserContexte

    ' Contexte specifique reseau
    Set g_oParserBoite = New CBoiteEPParser
    Set g_oBoiteP1 = New CBoiteEPInfo
    Set g_oBoiteP2 = New CBoiteEPInfo
    Set g_oRefFeP1 = New CPointRef
    Set g_oRefFeP2 = New CPointRef
    g_dTolReseau = 5#

    ' Pentes : 1 decimale (defaut CSymboPente.InitDefauts, ligne explicite pour trace)
    g_oSettings.oIndicPente.Decimales = 1

    AfficherFormulaire frmReseauEP

    CommandState.StartPrimitive New CSnapBoiteP1
End Sub

'==============================================================================
' Recherche de la cellule regard/grille la plus proche du clic
'
' Scanne le modele actif ET les fichiers attaches (references). Les origines
' issues d'une reference sont converties dans le repere du modele actif via
' ReferenceOrigin / MasterOrigin / ScaleFactor (meme approche que
' RechercheAltitude.bas de la commande V2).
'==============================================================================

'------------------------------------------------------------------------------
Public Function TrouverBoiteEPProche(oPt As Point3d, dRayon As Double, _
                                     oResult As CBoiteEPInfo) As Boolean
    TrouverBoiteEPProche = False
    If oResult Is Nothing Then Set oResult = New CBoiteEPInfo
    oResult.Vider

    Dim oScan As New ElementScanCriteria
    oScan.ExcludeAllTypes
    oScan.IncludeType msdElementTypeCellHeader

    Dim dMin As Double: dMin = dRayon
    Dim oBest As CBoiteEPInfo: Set oBest = Nothing

    ' 1) Modele actif
    ScannerBoiteDansModele ActiveModelReference, Nothing, oScan, oPt, dMin, oBest

    ' 2) Fichiers attaches : iterer par index (le For Each sur Attachments est
    '    fragile selon la version V8i, il peut echouer sans erreur visible).
    Dim oAttachments As Object
    Set oAttachments = ObtenirAttachments()
    Dim nCount As Long: nCount = 0
    On Error Resume Next
    If Not oAttachments Is Nothing Then nCount = oAttachments.Count
    On Error GoTo 0

    Dim i As Long
    For i = 1 To nCount
        Dim oAtt As Object
        Set oAtt = Nothing
        On Error Resume Next
        Set oAtt = oAttachments(i)
        On Error GoTo 0
        If Not (oAtt Is Nothing) Then
            If AttachmentAffiche(oAtt) Then
                ScannerBoiteDansModele oAtt, oAtt, oScan, oPt, dMin, oBest
            End If
        End If
    Next i

    If oBest Is Nothing Then Exit Function
    oResult.CopierDepuis oBest
    TrouverBoiteEPProche = True
End Function

'------------------------------------------------------------------------------
' Renvoie la collection des attachements du modele actif.
Private Function ObtenirAttachments() As Object
    Set ObtenirAttachments = Nothing
    On Error Resume Next
    Set ObtenirAttachments = ActiveModelReference.Attachments
    On Error GoTo 0
End Function

'------------------------------------------------------------------------------
' Scanne un modele ou une reference attachee. Les origines stockees dans oBest
' sont toujours exprimees dans le repere du modele actif.
Private Sub ScannerBoiteDansModele(oModel As Object, oAttachment As Object, _
        oScan As ElementScanCriteria, oPtClic As Point3d, _
        dMinDist As Double, oBest As CBoiteEPInfo)

    Dim oEnum As ElementEnumerator
    On Error Resume Next
    Set oEnum = oModel.Scan(oScan)
    If Err.Number <> 0 Or oEnum Is Nothing Then
        Err.Clear
        On Error GoTo 0
        Exit Sub
    End If
    On Error GoTo 0

    Do While oEnum.MoveNext
        Dim oElem As Element
        Set oElem = oEnum.Current
        If oElem.Type <> msdElementTypeCellHeader Then GoTo Suivant

        Dim oInfo As CBoiteEPInfo
        Set oInfo = g_oParserBoite.Lire(oElem)
        If Not oInfo.Valide Then GoTo Suivant

        ' Origine cellule -> repere maitre
        Dim ptSrc As Point3d, ptMaster As Point3d
        oInfo.CopierOrigine ptSrc
        TransformerPointVersMaitre oAttachment, ptSrc, ptMaster

        Dim dD As Double
        dD = Dist2DLoc(oPtClic, ptMaster)
        If dD < dMinDist Then
            dMinDist = dD
            oInfo.DefinirOrigine ptMaster
            oInfo.EstReference = Not (oAttachment Is Nothing)
            Set oInfo.oAttachment = oAttachment
            Set oBest = oInfo
        End If
Suivant:
    Loop
End Sub

'------------------------------------------------------------------------------
Private Function AttachmentAffiche(oAttachment As Object) As Boolean
    AttachmentAffiche = True
    On Error Resume Next
    AttachmentAffiche = CBool(oAttachment.IsDisplayed)
    If Err.Number <> 0 Then
        Err.Clear
        AttachmentAffiche = True
    End If
    On Error GoTo 0
End Function

'------------------------------------------------------------------------------
' Convertit une origine issue d'une reference vers le repere du modele actif.
'
' Verification sur DGN reel : MicroStation renvoie oCell.Origin dans un espace
' de coord DEJA compatible avec le master (identite). Le ScaleFactor
' d'attachement est une echelle graphique du CONTENU (taille visuelle), pas
' des positions -> ne pas l'appliquer aux coords.
'
' On conserve simplement la translation MasterOrigin - RefOrigin pour couvrir
' le cas ou le ref est place a un offset du master.
Private Sub TransformerPointVersMaitre(oAttachment As Object, _
        oPtSource As Point3d, oPtMaster As Point3d)

    oPtMaster = oPtSource
    If oAttachment Is Nothing Then Exit Sub

    Dim ptRefOrigin As Point3d, ptMasterOrigin As Point3d
    On Error Resume Next
    ptRefOrigin = oAttachment.ReferenceOrigin
    If Err.Number <> 0 Then Err.Clear
    ptMasterOrigin = oAttachment.MasterOrigin
    If Err.Number <> 0 Then Err.Clear
    On Error GoTo 0

    oPtMaster.X = ptMasterOrigin.X + (oPtSource.X - ptRefOrigin.X)
    oPtMaster.Y = ptMasterOrigin.Y + (oPtSource.Y - ptRefOrigin.Y)
    oPtMaster.Z = ptMasterOrigin.Z + (oPtSource.Z - ptRefOrigin.Z)
End Sub

'------------------------------------------------------------------------------
' Calcule le rapport UORsPerMasterUnit(actif) / UORsPerMasterUnit(ref).
' Renvoie 1 si l'un des deux n'est pas accessible.
Private Function RatioUORActifSurRef(oAttachment As Object) As Double
    RatioUORActifSurRef = 1#

    Dim dAct As Double: dAct = 0#
    Dim dRef As Double: dRef = 0#

    Dim oActive As Object
    Set oActive = ActiveModelReference

    On Error Resume Next

    dAct = CDbl(oActive.UORsPerMasterUnit)
    If Err.Number <> 0 Or dAct <= 0 Then Err.Clear: dAct = 0

    ' L'Attachment peut exposer UORsPerMasterUnit directement, ou via son
    ' ModelReference interne selon la version.
    dRef = CDbl(oAttachment.UORsPerMasterUnit)
    If Err.Number <> 0 Or dRef <= 0 Then
        Err.Clear
        dRef = CDbl(oAttachment.ModelReference.UORsPerMasterUnit)
        If Err.Number <> 0 Or dRef <= 0 Then Err.Clear: dRef = 0
    End If

    On Error GoTo 0

    If dAct > 0 And dRef > 0 Then RatioUORActifSurRef = dAct / dRef
End Function

'------------------------------------------------------------------------------
' Rayon de recherche courant (partage entre les etats, modifiable via UI).
Public Function TolReseau() As Double
    If g_dTolReseau <= 0 Then g_dTolReseau = 5#
    TolReseau = g_dTolReseau
End Function

'------------------------------------------------------------------------------
Private Function Dist2DLoc(oA As Point3d, oB As Point3d) As Double
    Dist2DLoc = Sqr((oB.X - oA.X) ^ 2 + (oB.Y - oA.Y) ^ 2)
End Function

'==============================================================================
' Utilitaires partages par les classes d'etat reseau
'==============================================================================

'------------------------------------------------------------------------------
' Charge un CPointRef avec les coordonnees XY du point snappe et l'altitude Fe
' de la cellule associee. Le point de reference sert au calcul de pente et au
' trace : c'est bien le snap qui compte, pas l'origine de la cellule.
Public Sub AlimenterPointRefFeSnap(oRef As CPointRef, _
                                    ptSnap As Point3d, oInfo As CBoiteEPInfo)
    oRef.DefinirPosition ptSnap
    oRef.Altitude = oInfo.ZFilEau
    oRef.Valide = oInfo.TrouveFilEau
End Sub

'------------------------------------------------------------------------------
' Texte court d'affichage d'une info reseau (utilise dans les prompts).
Public Function DecrireBoite(oInfo As CBoiteEPInfo) As String
    Dim s As String
    s = "Fe=" & Format$(oInfo.ZFilEau, "0.000")
    If oInfo.TrouveTampon Then s = s & "  T=" & Format$(oInfo.ZTampon, "0.000")
    If oInfo.TrouveProfondeur Then s = s & "  Prof=" & Format$(oInfo.Profondeur, "0.00")
    If oInfo.EstReference Then s = s & "  [ref]"
    DecrireBoite = s
End Function

'==============================================================================
' Diagnostic references (a lancer via : vba run [InterpolationTopoV2]DebugScanRefsBoiteEP)
'==============================================================================

'------------------------------------------------------------------------------
' Ouvre une boite d'info listant, pour chaque attachement :
'   - son nom / son chemin logique
'   - IsDisplayed
'   - nb total de CellHeader scannees
'   - nb de cellules BoiteEP valides (avec Fe:)
' Utile pour verifier que TrouverBoiteEPProche voit bien les cellules du ref.
Sub DebugScanRefsBoiteEP()
    If Not EnvironnementPret("Debug Scan Refs") Then Exit Sub
    If g_oParserBoite Is Nothing Then Set g_oParserBoite = New CBoiteEPParser

    Dim sRap As String
    sRap = "=== Modele actif ===" & vbCrLf
    sRap = sRap & ResumerScan(ActiveModelReference, Nothing) & vbCrLf

    Dim oAttachments As Object
    Set oAttachments = ObtenirAttachments()
    Dim nCount As Long: nCount = 0
    On Error Resume Next
    If Not oAttachments Is Nothing Then nCount = oAttachments.Count
    On Error GoTo 0

    sRap = sRap & vbCrLf & "=== Attachements : " & nCount & " ===" & vbCrLf

    Dim i As Long
    For i = 1 To nCount
        Dim oAtt As Object: Set oAtt = Nothing
        On Error Resume Next
        Set oAtt = oAttachments(i)
        On Error GoTo 0
        If oAtt Is Nothing Then
            sRap = sRap & vbCrLf & "[" & i & "] (nul)" & vbCrLf
        Else
            sRap = sRap & vbCrLf & "[" & i & "] " & DecrireAttachment(oAtt) & vbCrLf
            sRap = sRap & ResumerScan(oAtt, oAtt) & vbCrLf
        End If
    Next i

    MsgBox sRap, vbInformation, "Debug Scan Refs BoiteEP"
End Sub

Private Function DecrireAttachment(oAtt As Object) As String
    Dim s As String
    On Error Resume Next
    s = "IsDisplayed=" & CStr(oAtt.IsDisplayed)
    Err.Clear
    Dim sName As String
    sName = CStr(oAtt.LogicalName)
    If Err.Number <> 0 Then Err.Clear: sName = "(sans nom logique)"
    s = s & "  Name=""" & sName & """"
    Err.Clear
    Dim sFile As String
    sFile = CStr(oAtt.AttachFileName)
    If Err.Number = 0 Then s = s & "  File=""" & sFile & """"
    Err.Clear
    Dim dScale As Double
    dScale = oAtt.ScaleFactor
    If Err.Number = 0 Then s = s & vbCrLf & "    ScaleFactor=" & Format$(dScale, "0.000000")
    Err.Clear
    Dim dRatio As Double
    dRatio = RatioUORActifSurRef(oAtt)
    s = s & "  UOR ratio=" & Format$(dRatio, "0.000000")
    Dim ptMO As Point3d, ptRO As Point3d
    ptMO = oAtt.MasterOrigin
    If Err.Number = 0 Then s = s & vbCrLf & "    MasterOrigin=(" & _
        Format$(ptMO.X, "0.00") & ", " & Format$(ptMO.Y, "0.00") & ")"
    Err.Clear
    ptRO = oAtt.ReferenceOrigin
    If Err.Number = 0 Then s = s & "  RefOrigin=(" & _
        Format$(ptRO.X, "0.00") & ", " & Format$(ptRO.Y, "0.00") & ")"
    Err.Clear
    Dim tf As Transform3d
    tf = oAtt.Transform
    If Err.Number = 0 Then
        s = s & vbCrLf & "    Matrix RowX=(" & _
            Format$(tf.RowX.X, "0.000000") & ", " & _
            Format$(tf.RowX.Y, "0.000000") & ", " & _
            Format$(tf.RowX.Z, "0.000000") & ")"
    End If
    Err.Clear
    On Error GoTo 0
    DecrireAttachment = s
End Function

Private Function ResumerScan(oModel As Object, oAtt As Object) As String
    Dim oScan As New ElementScanCriteria
    oScan.ExcludeAllTypes
    oScan.IncludeType msdElementTypeCellHeader

    Dim oEnum As ElementEnumerator
    On Error Resume Next
    Set oEnum = oModel.Scan(oScan)
    If Err.Number <> 0 Or oEnum Is Nothing Then
        ResumerScan = "  -> Scan impossible (err " & Err.Number & ")"
        Err.Clear
        On Error GoTo 0
        Exit Function
    End If
    On Error GoTo 0

    Dim nCells As Long: nCells = 0
    Dim nValides As Long: nValides = 0
    Dim sExemples As String

    Do While oEnum.MoveNext
        Dim oElem As Element
        Set oElem = oEnum.Current
        If oElem.Type = msdElementTypeCellHeader Then
            nCells = nCells + 1
            Dim oInfo As CBoiteEPInfo
            Set oInfo = g_oParserBoite.Lire(oElem)
            If oInfo.Valide Then
                nValides = nValides + 1
                If Len(sExemples) < 600 Then
                    Dim pt As Point3d, ptM As Point3d
                    oInfo.CopierOrigine pt
                    TransformerPointVersMaitre oAtt, pt, ptM
                    sExemples = sExemples & _
                        "     Fe=" & Format$(oInfo.ZFilEau, "0.00") & _
                        "  ref=(" & Format$(pt.X, "0") & _
                                "," & Format$(pt.Y, "0") & ")" & _
                        "  master=(" & Format$(ptM.X, "0.00") & _
                                    "," & Format$(ptM.Y, "0.00") & ")" & vbCrLf
                End If
            End If
        End If
    Loop

    ResumerScan = "  -> CellHeader = " & nCells & _
                  " ; BoiteEP valides = " & nValides
    If Len(sExemples) > 0 Then ResumerScan = ResumerScan & vbCrLf & sExemples
End Function

Attribute VB_Name = "frmInterpolPonct"
Attribute VB_Base = "0{34DAC181-F794-4255-8C8B-224DBFDADE9F}{5275A017-8359-48C3-AD4A-AB29E2EE46FD}"
Attribute VB_GlobalNameSpace = False
Attribute VB_Creatable = False
Attribute VB_PredeclaredId = True
Attribute VB_Exposed = False
Attribute VB_TemplateDerived = False
Attribute VB_Customizable = False

'==============================================================================
' frmInterpolPonct - Formulaire de la commande Interpolation Ponctuelle
'
' Cadres :
'   Chemin principal : pente (%), DZ, checkbox
'   Rayonnement      : pente (%), DZ, checkbox
'   Decimales        : commun chemin + rayon
'   Cercle           : diametre, couleur, niveau
'   Texte            : comme modele, couleur, niveau
'   Etat             : P1, P2 (optionnel)
'
' Tous les controles sont crees au runtime dans ConstruireControles.
'==============================================================================
Option Explicit

Private m_oSettings As CMstSettings
Private m_bInit     As Boolean
Private m_bConstruit As Boolean

' --- Chemin principal ---
Private WithEvents chkCheminPente As MSForms.CheckBox
Attribute chkCheminPente.VB_VarHelpID = -1
Private WithEvents txtCheminPente As MSForms.TextBox
Attribute txtCheminPente.VB_VarHelpID = -1
Private WithEvents btnInverserCheminPente As MSForms.CommandButton
Attribute btnInverserCheminPente.VB_VarHelpID = -1
Private WithEvents chkCheminDZ As MSForms.CheckBox
Attribute chkCheminDZ.VB_VarHelpID = -1
Private WithEvents txtCheminDZ As MSForms.TextBox
Attribute txtCheminDZ.VB_VarHelpID = -1
Private WithEvents chkCheminIndPente As MSForms.CheckBox
Attribute chkCheminIndPente.VB_VarHelpID = -1
' --- Rayonnement ---
Private WithEvents chkRayonPente As MSForms.CheckBox
Attribute chkRayonPente.VB_VarHelpID = -1
Private WithEvents txtRayonPente As MSForms.TextBox
Attribute txtRayonPente.VB_VarHelpID = -1
Private WithEvents btnInverserRayonPente As MSForms.CommandButton
Attribute btnInverserRayonPente.VB_VarHelpID = -1
Private WithEvents chkRayonDZ As MSForms.CheckBox
Attribute chkRayonDZ.VB_VarHelpID = -1
Private WithEvents txtRayonDZ As MSForms.TextBox
Attribute txtRayonDZ.VB_VarHelpID = -1
' --- Rayonnement indicateur pente ---
Private WithEvents chkRayonIndPente As MSForms.CheckBox
Attribute chkRayonIndPente.VB_VarHelpID = -1
Private WithEvents txtPenteDec As MSForms.TextBox
Attribute txtPenteDec.VB_VarHelpID = -1
' --- Decimales ---
Private WithEvents txtDecimales As MSForms.TextBox
Attribute txtDecimales.VB_VarHelpID = -1
' --- Cercle ---
Private WithEvents txtDiametre As MSForms.TextBox
Attribute txtDiametre.VB_VarHelpID = -1
Private WithEvents txtCouleur As MSForms.TextBox
Attribute txtCouleur.VB_VarHelpID = -1
Private WithEvents cmbNiveau As MSForms.ComboBox
Attribute cmbNiveau.VB_VarHelpID = -1
' --- Texte ---
Private WithEvents chkTexteModele As MSForms.CheckBox
Attribute chkTexteModele.VB_VarHelpID = -1
Private WithEvents txtCouleurTexte As MSForms.TextBox
Attribute txtCouleurTexte.VB_VarHelpID = -1
Private WithEvents cmbNiveauTexte As MSForms.ComboBox
Attribute cmbNiveauTexte.VB_VarHelpID = -1
' --- Etat ---
Private lblP1       As MSForms.Label
Private lblP2       As MSForms.Label

'==============================================================================
' Construction des controles
'==============================================================================

Private Sub UserForm_Initialize()
    ConstruireControles
End Sub

Private Sub ConstruireControles()
    If m_bConstruit Then Exit Sub
    m_bConstruit = True

    Me.Caption = "Interpol. Ponctuelle"
    Me.Width = 212
    Me.Height = 514

    Dim dY As Double
    dY = 6

    ' --- Cadre Chemin principal -----------------------------------------------
    Dim fraChemin As MSForms.Frame
    Set fraChemin = Me.Controls.Add("Forms.Frame.1", "fraChemin")
    fraChemin.Caption = "Chemin principal (Vert)"
    fraChemin.Left = 6: fraChemin.Top = dY
    fraChemin.Width = 192: fraChemin.Height = 94

    Set chkCheminPente = fraChemin.Controls.Add("Forms.CheckBox.1", "chkCheminPente")
    chkCheminPente.Caption = "Pente (%)"
    chkCheminPente.Left = 6: chkCheminPente.Top = 10
    chkCheminPente.Width = 70: chkCheminPente.Height = 14

    Set txtCheminPente = fraChemin.Controls.Add("Forms.TextBox.1", "txtCheminPente")
    txtCheminPente.Left = 78: txtCheminPente.Top = 9
    txtCheminPente.Width = 48: txtCheminPente.Height = 16
    txtCheminPente.Text = "0": txtCheminPente.Enabled = False

    Set btnInverserCheminPente = fraChemin.Controls.Add("Forms.CommandButton.1", "btnInvChP")
    btnInverserCheminPente.Caption = "+/-"
    btnInverserCheminPente.Left = 130: btnInverserCheminPente.Top = 9
    btnInverserCheminPente.Width = 28: btnInverserCheminPente.Height = 16
    btnInverserCheminPente.Enabled = False

    Set chkCheminDZ = fraChemin.Controls.Add("Forms.CheckBox.1", "chkCheminDZ")
    chkCheminDZ.Caption = "DZ"
    chkCheminDZ.Left = 6: chkCheminDZ.Top = 32
    chkCheminDZ.Width = 36: chkCheminDZ.Height = 14

    Set txtCheminDZ = fraChemin.Controls.Add("Forms.TextBox.1", "txtCheminDZ")
    txtCheminDZ.Left = 44: txtCheminDZ.Top = 31
    txtCheminDZ.Width = 48: txtCheminDZ.Height = 16
    txtCheminDZ.Text = "0": txtCheminDZ.Enabled = False

    Set chkCheminIndPente = fraChemin.Controls.Add("Forms.CheckBox.1", "chkCheminIndPente")
    chkCheminIndPente.Caption = "Pente + fleche"
    chkCheminIndPente.Left = 6: chkCheminIndPente.Top = 52
    chkCheminIndPente.Width = 100: chkCheminIndPente.Height = 14

    CreerLabel fraChemin, "lblInfoChem", _
        "Pente auto si P2 selectionne", 6, 72, 180

    dY = dY + 100

    ' --- Cadre Rayonnement ----------------------------------------------------
    Dim fraRayon As MSForms.Frame
    Set fraRayon = Me.Controls.Add("Forms.Frame.1", "fraRayon")
    fraRayon.Caption = "Rayonnement (Jaune)"
    fraRayon.Left = 6: fraRayon.Top = dY
    fraRayon.Width = 192: fraRayon.Height = 72

    Set chkRayonPente = fraRayon.Controls.Add("Forms.CheckBox.1", "chkRayonPente")
    chkRayonPente.Caption = "Pente (%)"
    chkRayonPente.Left = 6: chkRayonPente.Top = 10
    chkRayonPente.Width = 70: chkRayonPente.Height = 14

    Set txtRayonPente = fraRayon.Controls.Add("Forms.TextBox.1", "txtRayonPente")
    txtRayonPente.Left = 78: txtRayonPente.Top = 9
    txtRayonPente.Width = 48: txtRayonPente.Height = 16
    txtRayonPente.Text = "0": txtRayonPente.Enabled = False

    Set btnInverserRayonPente = fraRayon.Controls.Add("Forms.CommandButton.1", "btnInvRP")
    btnInverserRayonPente.Caption = "+/-"
    btnInverserRayonPente.Left = 130: btnInverserRayonPente.Top = 9
    btnInverserRayonPente.Width = 28: btnInverserRayonPente.Height = 16
    btnInverserRayonPente.Enabled = False

    Set chkRayonDZ = fraRayon.Controls.Add("Forms.CheckBox.1", "chkRayonDZ")
    chkRayonDZ.Caption = "DZ"
    chkRayonDZ.Left = 6: chkRayonDZ.Top = 32
    chkRayonDZ.Width = 36: chkRayonDZ.Height = 14

    Set txtRayonDZ = fraRayon.Controls.Add("Forms.TextBox.1", "txtRayonDZ")
    txtRayonDZ.Left = 44: txtRayonDZ.Top = 31
    txtRayonDZ.Width = 48: txtRayonDZ.Height = 16
    txtRayonDZ.Text = "0": txtRayonDZ.Enabled = False

    Set chkRayonIndPente = fraRayon.Controls.Add("Forms.CheckBox.1", "chkRayonIndPente")
    chkRayonIndPente.Caption = "Pente + fleche"
    chkRayonIndPente.Left = 6: chkRayonIndPente.Top = 52
    chkRayonIndPente.Width = 100: chkRayonIndPente.Height = 14

    CreerLabel fraRayon, "lblPenteDec", "Dec.pente:", 108, 54, 44
    Set txtPenteDec = fraRayon.Controls.Add("Forms.TextBox.1", "txtPenteDec")
    txtPenteDec.Left = 154: txtPenteDec.Top = 51
    txtPenteDec.Width = 30: txtPenteDec.Height = 16

    dY = dY + 78

    ' --- Decimales ------------------------------------------------------------
    Dim fraDec As MSForms.Frame
    Set fraDec = Me.Controls.Add("Forms.Frame.1", "fraDec")
    fraDec.Caption = "Decimales (points crees)"
    fraDec.Left = 6: fraDec.Top = dY
    fraDec.Width = 192: fraDec.Height = 38

    Set txtDecimales = fraDec.Controls.Add("Forms.TextBox.1", "txtDecimales")
    txtDecimales.Left = 6: txtDecimales.Top = 12
    txtDecimales.Width = 24: txtDecimales.Height = 16
    txtDecimales.Text = "2"

    dY = dY + 44

    ' --- Cadre Cercle ---------------------------------------------------------
    Dim fraCercle As MSForms.Frame
    Set fraCercle = Me.Controls.Add("Forms.Frame.1", "fraCercle")
    fraCercle.Caption = "Cercle"
    fraCercle.Left = 6: fraCercle.Top = dY
    fraCercle.Width = 192: fraCercle.Height = 76

    CreerLabel fraCercle, "lblDiam", "Diametre :", 6, 10, 48
    Set txtDiametre = fraCercle.Controls.Add("Forms.TextBox.1", "txtDiametre")
    txtDiametre.Left = 56: txtDiametre.Top = 8
    txtDiametre.Width = 48: txtDiametre.Height = 16

    CreerLabel fraCercle, "lblCoul", "Couleur :", 6, 30, 42
    Set txtCouleur = fraCercle.Controls.Add("Forms.TextBox.1", "txtCouleur")
    txtCouleur.Left = 56: txtCouleur.Top = 28
    txtCouleur.Width = 30: txtCouleur.Height = 16

    CreerLabel fraCercle, "lblNiv", "Niveau :", 6, 50, 42
    Set cmbNiveau = fraCercle.Controls.Add("Forms.ComboBox.1", "cmbNiveau")
    cmbNiveau.Left = 56: cmbNiveau.Top = 48
    cmbNiveau.Width = 130: cmbNiveau.Height = 16

    dY = dY + 82

    ' --- Cadre Texte ----------------------------------------------------------
    Dim fraTexte As MSForms.Frame
    Set fraTexte = Me.Controls.Add("Forms.Frame.1", "fraTexte")
    fraTexte.Caption = "Texte altitude"
    fraTexte.Left = 6: fraTexte.Top = dY
    fraTexte.Width = 192: fraTexte.Height = 76

    Set chkTexteModele = fraTexte.Controls.Add("Forms.CheckBox.1", "chkTexteModele")
    chkTexteModele.Caption = "Memes attributs que P1"
    chkTexteModele.Left = 6: chkTexteModele.Top = 10
    chkTexteModele.Width = 180: chkTexteModele.Height = 14
    chkTexteModele.Value = True

    CreerLabel fraTexte, "lblCoulTxt", "Couleur :", 6, 30, 42
    Set txtCouleurTexte = fraTexte.Controls.Add("Forms.TextBox.1", "txtCouleurTexte")
    txtCouleurTexte.Left = 56: txtCouleurTexte.Top = 28
    txtCouleurTexte.Width = 30: txtCouleurTexte.Height = 16

    CreerLabel fraTexte, "lblNivTxt", "Niveau :", 6, 50, 42
    Set cmbNiveauTexte = fraTexte.Controls.Add("Forms.ComboBox.1", "cmbNiveauTexte")
    cmbNiveauTexte.Left = 56: cmbNiveauTexte.Top = 48
    cmbNiveauTexte.Width = 130: cmbNiveauTexte.Height = 16

    dY = dY + 82

    ' --- Cadre Etat -----------------------------------------------------------
    Dim fraEtat As MSForms.Frame
    Set fraEtat = Me.Controls.Add("Forms.Frame.1", "fraEtat")
    fraEtat.Caption = "Etat"
    fraEtat.Left = 6: fraEtat.Top = dY
    fraEtat.Width = 192: fraEtat.Height = 44
    

    Set lblP1 = CreerLabel(fraEtat, "lblP1", "P1 : -", 6, 12, 180)
    Set lblP2 = CreerLabel(fraEtat, "lblP2", "P2 : -", 6, 24, 180)
End Sub

'------------------------------------------------------------------------------
Private Function CreerLabel(oParent As MSForms.Frame, sNom As String, _
                            sCaption As String, dLeft As Double, dTop As Double, _
                            dWidth As Double) As MSForms.Label
    Set CreerLabel = oParent.Controls.Add("Forms.Label.1", sNom)
    CreerLabel.Caption = sCaption
    CreerLabel.Left = dLeft: CreerLabel.Top = dTop
    CreerLabel.Width = dWidth: CreerLabel.Height = 12
End Function

'==============================================================================
' Initialisation
'==============================================================================

Sub Initialiser(oSettings As CMstSettings)
    ConstruireControles
    Set m_oSettings = oSettings
    m_bInit = True

    ' Chemin principal
    chkCheminPente.Value = m_oSettings.oChemin.PenteActive
    txtCheminPente.Text = Format$(m_oSettings.oChemin.Pente, "0.00")
    txtCheminPente.Enabled = m_oSettings.oChemin.PenteActive
    btnInverserCheminPente.Enabled = m_oSettings.oChemin.PenteActive
    chkCheminDZ.Value = m_oSettings.oChemin.DZActive
    txtCheminDZ.Text = Format$(m_oSettings.oChemin.DZ, "0.00")
    txtCheminDZ.Enabled = m_oSettings.oChemin.DZActive
    chkCheminIndPente.Value = m_oSettings.bCheminIndicPente

    ' Rayonnement
    chkRayonPente.Value = m_oSettings.oRayon.PenteActive
    txtRayonPente.Text = Format$(m_oSettings.oRayon.Pente, "0.00")
    txtRayonPente.Enabled = m_oSettings.oRayon.PenteActive
    btnInverserRayonPente.Enabled = m_oSettings.oRayon.PenteActive
    chkRayonDZ.Value = m_oSettings.oRayon.DZActive
    txtRayonDZ.Text = Format$(m_oSettings.oRayon.DZ, "0.00")
    txtRayonDZ.Enabled = m_oSettings.oRayon.DZActive
    chkRayonIndPente.Value = m_oSettings.bRayonIndicPente
    txtPenteDec.Text = CStr(m_oSettings.oIndicPente.Decimales)

    ' Decimales
    txtDecimales.Text = CStr(m_oSettings.nPonctDecimales)

    ' Cercle
    txtDiametre.Text = Format$(m_oSettings.oCercle.Diametre, "0.00")
    txtCouleur.Text = CStr(m_oSettings.oCercle.Couleur)
    RemplirNiveaux cmbNiveau

    ' Texte
    chkTexteModele.Value = m_oSettings.oTexte.CommeModele
    txtCouleurTexte.Text = CStr(m_oSettings.oTexte.Couleur)
    RemplirNiveaux cmbNiveauTexte
    ActiverChampsTexte

    ReinitialiserEtat
    m_bInit = False
End Sub

'------------------------------------------------------------------------------
Private Sub RemplirNiveaux(cmb As MSForms.ComboBox)
    cmb.Clear
    cmb.AddItem ""
    Dim oLvl As Level
    For Each oLvl In ActiveDesignFile.Levels
        cmb.AddItem oLvl.Number & " : " & oLvl.Name
    Next
    cmb.ListIndex = 0
End Sub

Private Sub ActiverChampsTexte()
    Dim bLibre As Boolean
    bLibre = Not m_oSettings.oTexte.CommeModele
    txtCouleurTexte.Enabled = bLibre
    cmbNiveauTexte.Enabled = bLibre
End Sub

'==============================================================================
' Mise a jour par les classes de commande
'==============================================================================

Sub AfficherP1(oP As CPointRef)
    lblP1.Caption = "P1 : " & oP.Altitude
End Sub

Sub AfficherP2(oP As CPointRef)
    lblP2.Caption = "P2 : " & oP.Altitude
End Sub

Sub ReinitialiserEtat()
    lblP1.Caption = "P1 : -"
    lblP2.Caption = "P2 : -"
End Sub

Sub RafraichirTexte()
    If m_oSettings Is Nothing Then Exit Sub
    m_bInit = True
    txtCouleurTexte.Text = CStr(m_oSettings.oTexte.Couleur)
    cmbNiveauTexte.Text = m_oSettings.oTexte.NomNiveau
    m_bInit = False
End Sub

Sub RafraichirChemin()
    If m_oSettings Is Nothing Then Exit Sub
    m_bInit = True
    chkCheminPente.Value = m_oSettings.oChemin.PenteActive
    txtCheminPente.Text = Format$(m_oSettings.oChemin.Pente, "0.00")
    txtCheminPente.Enabled = m_oSettings.oChemin.PenteActive
    btnInverserCheminPente.Enabled = m_oSettings.oChemin.PenteActive
    m_bInit = False
End Sub

'==============================================================================
' Evenements Chemin principal
'==============================================================================

Private Sub chkCheminPente_Change()
    If m_bInit Then Exit Sub
    If m_oSettings Is Nothing Then Exit Sub
    m_oSettings.oChemin.PenteActive = (chkCheminPente.Value = True)
    txtCheminPente.Enabled = m_oSettings.oChemin.PenteActive
    btnInverserCheminPente.Enabled = m_oSettings.oChemin.PenteActive
End Sub

Private Sub txtCheminPente_Change()
    If m_bInit Then Exit Sub
    If m_oSettings Is Nothing Then Exit Sub
    m_oSettings.oChemin.Pente = Val(Replace(Trim$(txtCheminPente.Text), ",", "."))
End Sub

Private Sub txtCheminPente_KeyDown(ByVal KeyCode As MSForms.ReturnInteger, _
                                    ByVal Shift As Integer)
    If KeyCode = vbKeyReturn And Not m_oSettings Is Nothing Then _
        txtCheminPente.Text = Format$(m_oSettings.oChemin.Pente, "0.00")
End Sub

Private Sub btnInverserCheminPente_Click()
    If m_oSettings Is Nothing Then Exit Sub
    m_oSettings.oChemin.Pente = -m_oSettings.oChemin.Pente
    txtCheminPente.Text = Format$(m_oSettings.oChemin.Pente, "0.00")
End Sub

Private Sub chkCheminDZ_Change()
    If m_bInit Then Exit Sub
    If m_oSettings Is Nothing Then Exit Sub
    m_oSettings.oChemin.DZActive = (chkCheminDZ.Value = True)
    txtCheminDZ.Enabled = m_oSettings.oChemin.DZActive
End Sub

Private Sub chkCheminIndPente_Change()
    If m_bInit Then Exit Sub
    If m_oSettings Is Nothing Then Exit Sub
    m_oSettings.bCheminIndicPente = (chkCheminIndPente.Value = True)
End Sub

Private Sub txtCheminDZ_Change()
    If m_bInit Then Exit Sub
    If m_oSettings Is Nothing Then Exit Sub
    m_oSettings.oChemin.DZ = Val(Replace(Trim$(txtCheminDZ.Text), ",", "."))
End Sub

Private Sub txtCheminDZ_KeyDown(ByVal KeyCode As MSForms.ReturnInteger, _
                                 ByVal Shift As Integer)
    If KeyCode = vbKeyReturn And Not m_oSettings Is Nothing Then _
        txtCheminDZ.Text = Format$(m_oSettings.oChemin.DZ, "0.00")
End Sub

'==============================================================================
' Evenements Rayonnement
'==============================================================================

Private Sub chkRayonPente_Change()
    If m_bInit Then Exit Sub
    If m_oSettings Is Nothing Then Exit Sub
    m_oSettings.oRayon.PenteActive = (chkRayonPente.Value = True)
    txtRayonPente.Enabled = m_oSettings.oRayon.PenteActive
    btnInverserRayonPente.Enabled = m_oSettings.oRayon.PenteActive
End Sub

Private Sub txtRayonPente_Change()
    If m_bInit Then Exit Sub
    If m_oSettings Is Nothing Then Exit Sub
    m_oSettings.oRayon.Pente = Val(Replace(Trim$(txtRayonPente.Text), ",", "."))
End Sub

Private Sub txtRayonPente_KeyDown(ByVal KeyCode As MSForms.ReturnInteger, _
                                   ByVal Shift As Integer)
    If KeyCode = vbKeyReturn And Not m_oSettings Is Nothing Then _
        txtRayonPente.Text = Format$(m_oSettings.oRayon.Pente, "0.00")
End Sub

Private Sub btnInverserRayonPente_Click()
    If m_oSettings Is Nothing Then Exit Sub
    m_oSettings.oRayon.Pente = -m_oSettings.oRayon.Pente
    txtRayonPente.Text = Format$(m_oSettings.oRayon.Pente, "0.00")
End Sub

Private Sub chkRayonDZ_Change()
    If m_bInit Then Exit Sub
    If m_oSettings Is Nothing Then Exit Sub
    m_oSettings.oRayon.DZActive = (chkRayonDZ.Value = True)
    txtRayonDZ.Enabled = m_oSettings.oRayon.DZActive
End Sub

Private Sub txtRayonDZ_Change()
    If m_bInit Then Exit Sub
    If m_oSettings Is Nothing Then Exit Sub
    m_oSettings.oRayon.DZ = Val(Replace(Trim$(txtRayonDZ.Text), ",", "."))
End Sub

Private Sub txtRayonDZ_KeyDown(ByVal KeyCode As MSForms.ReturnInteger, _
                                ByVal Shift As Integer)
    If KeyCode = vbKeyReturn And Not m_oSettings Is Nothing Then _
        txtRayonDZ.Text = Format$(m_oSettings.oRayon.DZ, "0.00")
End Sub

Private Sub chkRayonIndPente_Change()
    If m_bInit Then Exit Sub
    If m_oSettings Is Nothing Then Exit Sub
    m_oSettings.bRayonIndicPente = (chkRayonIndPente.Value = True)
End Sub

Private Sub txtPenteDec_Change()
    If m_bInit Then Exit Sub
    If m_oSettings Is Nothing Then Exit Sub
    Dim nDec As Integer
    nDec = CInt(Val(Trim$(txtPenteDec.Text)))
    If nDec >= 0 And nDec <= 6 Then m_oSettings.oIndicPente.Decimales = nDec
End Sub

Private Sub txtPenteDec_KeyDown(ByVal KeyCode As MSForms.ReturnInteger, _
                                 ByVal Shift As Integer)
    If KeyCode = vbKeyReturn And Not m_oSettings Is Nothing Then _
        txtPenteDec.Text = CStr(m_oSettings.oIndicPente.Decimales)
End Sub

'==============================================================================
' Evenements Decimales
'==============================================================================

Private Sub txtDecimales_Change()
    If m_bInit Then Exit Sub
    If m_oSettings Is Nothing Then Exit Sub
    Dim nDec As Integer
    nDec = CInt(Val(Trim$(txtDecimales.Text)))
    If nDec >= 0 And nDec <= 6 Then m_oSettings.nPonctDecimales = nDec
End Sub

Private Sub txtDecimales_KeyDown(ByVal KeyCode As MSForms.ReturnInteger, _
                                  ByVal Shift As Integer)
    If KeyCode = vbKeyReturn And Not m_oSettings Is Nothing Then _
        txtDecimales.Text = CStr(m_oSettings.nPonctDecimales)
End Sub

'==============================================================================
' Evenements Cercle
'==============================================================================

Private Sub txtDiametre_Change()
    If m_bInit Then Exit Sub
    If m_oSettings Is Nothing Then Exit Sub
    Dim dDiam As Double
    dDiam = Val(Replace(Trim$(txtDiametre.Text), ",", "."))
    If dDiam > 0 Then m_oSettings.oCercle.Diametre = dDiam
End Sub

Private Sub txtCouleur_Change()
    If m_bInit Then Exit Sub
    If m_oSettings Is Nothing Then Exit Sub
    Dim sVal As String: sVal = Trim$(txtCouleur.Text)
    If sVal = "" Then Exit Sub
    Dim nCoul As Long: nCoul = CLng(Val(sVal))
    If nCoul >= 0 And nCoul <= 255 Then m_oSettings.oCercle.Couleur = nCoul
End Sub

Private Sub cmbNiveau_Change()
    If m_bInit Then Exit Sub
    If m_oSettings Is Nothing Then Exit Sub
    m_oSettings.oCercle.NomNiveau = ExtraireNiveau(cmbNiveau.Text)
End Sub

'==============================================================================
' Evenements Texte
'==============================================================================

Private Sub chkTexteModele_Change()
    If m_bInit Then Exit Sub
    If m_oSettings Is Nothing Then Exit Sub
    m_oSettings.oTexte.CommeModele = (chkTexteModele.Value = True)
    ActiverChampsTexte
    If m_oSettings.oTexte.CommeModele And m_oSettings.TextModeleDisponible Then
        m_oSettings.oTexte.ChargerDepuisElement m_oSettings.oTextModele
        RafraichirTexte
    End If
End Sub

Private Sub txtCouleurTexte_Change()
    If m_bInit Then Exit Sub
    If m_oSettings Is Nothing Then Exit Sub
    Dim sVal As String: sVal = Trim$(txtCouleurTexte.Text)
    If sVal = "" Then Exit Sub
    Dim nCoul As Long: nCoul = CLng(Val(sVal))
    If nCoul >= 0 And nCoul <= 255 Then m_oSettings.oTexte.Couleur = nCoul
End Sub

Private Sub cmbNiveauTexte_Change()
    If m_bInit Then Exit Sub
    If m_oSettings Is Nothing Then Exit Sub
    m_oSettings.oTexte.NomNiveau = ExtraireNiveau(cmbNiveauTexte.Text)
End Sub

'------------------------------------------------------------------------------
Private Function ExtraireNiveau(ByVal sItem As String) As String
    sItem = Trim$(sItem)
    If InStr(sItem, " : ") > 0 Then
        ExtraireNiveau = Trim$(Left$(sItem, InStr(sItem, " : ") - 1))
    Else
        ExtraireNiveau = sItem
    End If
End Function

'==============================================================================
' Fermeture
'==============================================================================

Private Sub UserForm_QueryClose(Cancel As Integer, CloseMode As Integer)
    If CloseMode = vbFormControlMenu Then
        Cancel = 1
        Me.Hide
        CommandState.StartDefaultCommand
    End If
End Sub

Attribute VB_Name = "frmInterpolation"
Attribute VB_Base = "0{B946E56B-6A97-421A-9007-49F954093DCD}{213C02BD-811F-487F-B5E7-C93CF7251C32}"
Attribute VB_GlobalNameSpace = False
Attribute VB_Creatable = False
Attribute VB_PredeclaredId = True
Attribute VB_Exposed = False
Attribute VB_TemplateDerived = False
Attribute VB_Customizable = False

'==============================================================================
' frmInterpolation - Formulaire "Tool Settings" de la commande Interpolation Topo V2
'
' Fonctionne en mode modeless : reste visible pendant toute la commande.
' Lit et ecrit g_oSettings (CMstSettings).
' Mise a jour de l'etat (P1, P2, segment) par les classes de commande.
'
' IMPORTANT - CONSTRUCTION AU RUNTIME :
'   Tous les controles sont crees par code dans ConstruireControles (appele par
'   UserForm_Initialize). Le .frm ne decrit donc que le formulaire vide : aucun
'   fichier .frx n'est necessaire et le fichier reste versionnable en texte.
'
'   Si l'import du .frm echoue malgre tout : dans l'editeur VBA, Insertion >
'   UserForm, nommer le formulaire frmInterpolation, puis coller tout le code
'   ci-dessous (a partir de Option Explicit) dans son module.
'
' Controles (crees au runtime) :
'   fraCercle
'     txtDiametre    TextBox  - diametre du cercle (Double > 0)
'     txtCouleur     TextBox  - index couleur MicroStation 0-255
'     cmbNiveau      ComboBox - niveaux du fichier DGN (vide = niveau P1)
'   fraTexte
'     chkTexteModele CheckBox - True = memes attributs que le texte P1 (defaut)
'     txtCouleurTexte TextBox - couleur du texte cree (si case decochee)
'     cmbNiveauTexte ComboBox - niveau du texte cree (si case decochee)
'   fraEtat
'     lblP1          Label    - affiche "P1 : <altitude>" apres selection
'     lblP2          Label    - affiche "P2 : <altitude>" apres selection
'     lblSegment     Label    - affiche "Pente=x%  Gisement=x gon"
'
' Les saisies sont validees en continu (evenement Change) : la derniere valeur
' valide est conservee dans les parametres, une saisie invalide est ignoree.
' Entree dans un champ reformate l'affichage depuis la valeur courante.
'==============================================================================
Option Explicit

Private m_oSettings As CMstSettings  ' reference aux parametres de la commande
Private m_bInit     As Boolean       ' True pendant l'initialisation (bloque les evenements Change)
Private m_bConstruit As Boolean      ' True quand les controles ont ete crees

' Controles crees au runtime. WithEvents sur les champs de saisie :
' les procedures txtDiametre_Change etc. recoivent ainsi leurs evenements.
Private WithEvents txtDiametre As MSForms.TextBox
Attribute txtDiametre.VB_VarHelpID = -1
Private WithEvents txtCouleur  As MSForms.TextBox
Attribute txtCouleur.VB_VarHelpID = -1
Private WithEvents cmbNiveau   As MSForms.ComboBox
Attribute cmbNiveau.VB_VarHelpID = -1
Private WithEvents chkTexteModele As MSForms.CheckBox
Attribute chkTexteModele.VB_VarHelpID = -1
Private WithEvents txtCouleurTexte As MSForms.TextBox
Attribute txtCouleurTexte.VB_VarHelpID = -1
Private WithEvents cmbNiveauTexte As MSForms.ComboBox
Attribute cmbNiveauTexte.VB_VarHelpID = -1
Private WithEvents txtDecimales As MSForms.TextBox
Attribute txtDecimales.VB_VarHelpID = -1
Private WithEvents chkPente As MSForms.CheckBox
Attribute chkPente.VB_VarHelpID = -1
Private WithEvents txtPente As MSForms.TextBox
Attribute txtPente.VB_VarHelpID = -1
Private WithEvents btnInverserPente As MSForms.CommandButton
Attribute btnInverserPente.VB_VarHelpID = -1
Private WithEvents chkDecalageFixe As MSForms.CheckBox
Attribute chkDecalageFixe.VB_VarHelpID = -1
Private WithEvents txtDecalageDZ As MSForms.TextBox
Attribute txtDecalageDZ.VB_VarHelpID = -1
Private WithEvents chkDecalIndPente As MSForms.CheckBox
Attribute chkDecalIndPente.VB_VarHelpID = -1
Private WithEvents chkPentePerso As MSForms.CheckBox
Attribute chkPentePerso.VB_VarHelpID = -1
Private WithEvents txtPenteH As MSForms.TextBox
Attribute txtPenteH.VB_VarHelpID = -1
Private WithEvents txtPenteL As MSForms.TextBox
Attribute txtPenteL.VB_VarHelpID = -1
Private WithEvents cmbPenteNiveau As MSForms.ComboBox
Attribute cmbPenteNiveau.VB_VarHelpID = -1
Private WithEvents txtPenteCoulTxt As MSForms.TextBox
Attribute txtPenteCoulTxt.VB_VarHelpID = -1
Private WithEvents txtPenteCoulFl As MSForms.TextBox
Attribute txtPenteCoulFl.VB_VarHelpID = -1
Private WithEvents txtPenteFlLong As MSForms.TextBox
Attribute txtPenteFlLong.VB_VarHelpID = -1
Private WithEvents txtPenteDec As MSForms.TextBox
Attribute txtPenteDec.VB_VarHelpID = -1
Private WithEvents btnRetourInterp As MSForms.CommandButton
Attribute btnRetourInterp.VB_VarHelpID = -1
Private WithEvents btnPlacerPente As MSForms.CommandButton
Attribute btnPlacerPente.VB_VarHelpID = -1
Private WithEvents btnChemin As MSForms.CommandButton
Attribute btnChemin.VB_VarHelpID = -1
Private lblP1       As MSForms.Label
Private lblP2       As MSForms.Label
Private lblSegment  As MSForms.Label

'==============================================================================
' Construction des controles
'==============================================================================

Private Sub UserForm_Initialize()
    ConstruireControles
End Sub

'------------------------------------------------------------------------------
' Cree tous les controles par code (dimensions en points).
Private Sub ConstruireControles()
    If m_bConstruit Then Exit Sub
    m_bConstruit = True

    Me.Caption = "Interpolation Topo"
    Me.Width = 212
    Me.Height = 670

    ' --- Cadre Cercle -------------------------------------------------------
    Dim fraCercle As MSForms.Frame
    Set fraCercle = Me.Controls.Add("Forms.Frame.1", "fraCercle")
    fraCercle.Caption = "Cercle si Alti est un texte"
    fraCercle.Left = 6: fraCercle.Top = 6
    fraCercle.Width = 192: fraCercle.Height = 126

    CreerLabel fraCercle, "lblDiametre", "Diametre (unites maitre) :", 6, 10, 178
    Set txtDiametre = fraCercle.Controls.Add("Forms.TextBox.1", "txtDiametre")
    txtDiametre.Left = 6: txtDiametre.Top = 24
    txtDiametre.Width = 48: txtDiametre.Height = 16

    CreerLabel fraCercle, "lblCouleur", "Couleur (index MicroStation 0-255) :", 6, 46, 178
    Set txtCouleur = fraCercle.Controls.Add("Forms.TextBox.1", "txtCouleur")
    txtCouleur.Left = 6: txtCouleur.Top = 60
    txtCouleur.Width = 30: txtCouleur.Height = 16

    Dim lblInfo As MSForms.Label
    Set lblInfo = CreerLabel(fraCercle, "lblInfoCouleur", _
        "0=blanc 1=bleu 2=vert 3=rouge 4=jaune 6=orange", 42, 62, 146)
    lblInfo.Font.Size = 7

    CreerLabel fraCercle, "lblNiveau", "Niveau (vide = niveau du texte P1) :", 6, 82, 178
    Set cmbNiveau = fraCercle.Controls.Add("Forms.ComboBox.1", "cmbNiveau")
    cmbNiveau.Left = 6: cmbNiveau.Top = 96
    cmbNiveau.Width = 180: cmbNiveau.Height = 16

    ' --- Cadre Texte altitude ------------------------------------------------
    Dim fraTexte As MSForms.Frame
    Set fraTexte = Me.Controls.Add("Forms.Frame.1", "fraTexte")
    fraTexte.Caption = "Texte altitude si alti est un texte"
    fraTexte.Left = 6: fraTexte.Top = 138
    fraTexte.Width = 192: fraTexte.Height = 126

    Set chkTexteModele = fraTexte.Controls.Add("Forms.CheckBox.1", "chkTexteModele")
    chkTexteModele.Caption = "Memes attributs que le texte P1"
    chkTexteModele.Left = 6: chkTexteModele.Top = 10
    chkTexteModele.Width = 180: chkTexteModele.Height = 14
    chkTexteModele.Value = True

    CreerLabel fraTexte, "lblCouleurTexte", "Couleur (index MicroStation 0-255) :", 6, 28, 178
    Set txtCouleurTexte = fraTexte.Controls.Add("Forms.TextBox.1", "txtCouleurTexte")
    txtCouleurTexte.Left = 6: txtCouleurTexte.Top = 42
    txtCouleurTexte.Width = 30: txtCouleurTexte.Height = 16

    CreerLabel fraTexte, "lblNiveauTexte", "Niveau (vide = niveau du texte P1) :", 6, 64, 178
    Set cmbNiveauTexte = fraTexte.Controls.Add("Forms.ComboBox.1", "cmbNiveauTexte")
    cmbNiveauTexte.Left = 6: cmbNiveauTexte.Top = 78
    cmbNiveauTexte.Width = 180: cmbNiveauTexte.Height = 16

    CreerLabel fraTexte, "lblDecimales", "Decimales :", 6, 100, 54
    Set txtDecimales = fraTexte.Controls.Add("Forms.TextBox.1", "txtDecimales")
    txtDecimales.Left = 62: txtDecimales.Top = 98
    txtDecimales.Width = 24: txtDecimales.Height = 16
    txtDecimales.Text = "2"

    ' --- Cadre Pente decalage -----------------------------------------------
    Dim fraPente As MSForms.Frame
    Set fraPente = Me.Controls.Add("Forms.Frame.1", "fraPente")
    fraPente.Caption = "Pente decalage"
    fraPente.Left = 6: fraPente.Top = 270
    fraPente.Width = 192: fraPente.Height = 114

    Set chkPente = fraPente.Controls.Add("Forms.CheckBox.1", "chkPente")
    chkPente.Caption = "Appliquer pente transversale"
    chkPente.Left = 6: chkPente.Top = 10
    chkPente.Width = 180: chkPente.Height = 14
    chkPente.Value = False

    CreerLabel fraPente, "lblPente", "Pente (%) :", 6, 30, 60
    Set txtPente = fraPente.Controls.Add("Forms.TextBox.1", "txtPente")
    txtPente.Left = 68: txtPente.Top = 28
    txtPente.Width = 48: txtPente.Height = 16
    txtPente.Text = "0"
    txtPente.Enabled = False

    Set btnInverserPente = fraPente.Controls.Add("Forms.CommandButton.1", "btnInverserPente")
    btnInverserPente.Caption = "+/-"
    btnInverserPente.Left = 122: btnInverserPente.Top = 28
    btnInverserPente.Width = 28: btnInverserPente.Height = 16
    btnInverserPente.Enabled = False

    Set chkDecalageFixe = fraPente.Controls.Add("Forms.CheckBox.1", "chkDecalageFixe")
    chkDecalageFixe.Caption = "Decalage fixe DZ"
    chkDecalageFixe.Left = 6: chkDecalageFixe.Top = 50
    chkDecalageFixe.Width = 180: chkDecalageFixe.Height = 14
    chkDecalageFixe.Value = False

    CreerLabel fraPente, "lblDZ", "DZ :", 6, 70, 24
    Set txtDecalageDZ = fraPente.Controls.Add("Forms.TextBox.1", "txtDecalageDZ")
    txtDecalageDZ.Left = 32: txtDecalageDZ.Top = 68
    txtDecalageDZ.Width = 48: txtDecalageDZ.Height = 16
    txtDecalageDZ.Text = "0"
    txtDecalageDZ.Enabled = False

    Set chkDecalIndPente = fraPente.Controls.Add("Forms.CheckBox.1", "chkDecalIndPente")
    chkDecalIndPente.Caption = "Pente + fleche"
    chkDecalIndPente.Left = 6: chkDecalIndPente.Top = 90
    chkDecalIndPente.Width = 180: chkDecalIndPente.Height = 14
    chkDecalIndPente.Value = False

    ' --- Cadre Indicateur pente ---------------------------------------------
    Dim fraIndPente As MSForms.Frame
    Set fraIndPente = Me.Controls.Add("Forms.Frame.1", "fraIndPente")
    fraIndPente.Caption = "Indicateur pente"
    fraIndPente.Left = 6: fraIndPente.Top = 390
    fraIndPente.Width = 192: fraIndPente.Height = 90

    Set chkPentePerso = fraIndPente.Controls.Add("Forms.CheckBox.1", "chkPentePerso")
    chkPentePerso.Caption = "Personnaliser"
    chkPentePerso.Left = 6: chkPentePerso.Top = 10
    chkPentePerso.Width = 180: chkPentePerso.Height = 14
    chkPentePerso.Value = False

    CreerLabel fraIndPente, "lblPenteH", "H:", 6, 30, 12
    Set txtPenteH = fraIndPente.Controls.Add("Forms.TextBox.1", "txtPenteH")
    txtPenteH.Left = 20: txtPenteH.Top = 28: txtPenteH.Width = 40: txtPenteH.Height = 16
    txtPenteH.Enabled = False

    CreerLabel fraIndPente, "lblPenteL", "L:", 68, 30, 12
    Set txtPenteL = fraIndPente.Controls.Add("Forms.TextBox.1", "txtPenteL")
    txtPenteL.Left = 82: txtPenteL.Top = 28: txtPenteL.Width = 40: txtPenteL.Height = 16
    txtPenteL.Enabled = False

    CreerLabel fraIndPente, "lblPenteDec", "Dec:", 128, 30, 22
    Set txtPenteDec = fraIndPente.Controls.Add("Forms.TextBox.1", "txtPenteDec")
    txtPenteDec.Left = 152: txtPenteDec.Top = 28: txtPenteDec.Width = 34: txtPenteDec.Height = 16

    CreerLabel fraIndPente, "lblPenteNiv", "Niv:", 6, 50, 18
    Set cmbPenteNiveau = fraIndPente.Controls.Add("Forms.ComboBox.1", "cmbPenteNiveau")
    cmbPenteNiveau.Left = 28: cmbPenteNiveau.Top = 48
    cmbPenteNiveau.Width = 158: cmbPenteNiveau.Height = 16
    cmbPenteNiveau.Enabled = False

    CreerLabel fraIndPente, "lblPCTxt", "C.txt:", 6, 70, 26
    Set txtPenteCoulTxt = fraIndPente.Controls.Add("Forms.TextBox.1", "txtPenteCoulTxt")
    txtPenteCoulTxt.Left = 34: txtPenteCoulTxt.Top = 68
    txtPenteCoulTxt.Width = 24: txtPenteCoulTxt.Height = 16
    txtPenteCoulTxt.Enabled = False

    CreerLabel fraIndPente, "lblPCFl", "C.fl:", 66, 70, 22
    Set txtPenteCoulFl = fraIndPente.Controls.Add("Forms.TextBox.1", "txtPenteCoulFl")
    txtPenteCoulFl.Left = 90: txtPenteCoulFl.Top = 68
    txtPenteCoulFl.Width = 24: txtPenteCoulFl.Height = 16
    txtPenteCoulFl.Enabled = False

    CreerLabel fraIndPente, "lblPFlLong", "Long:", 122, 70, 24
    Set txtPenteFlLong = fraIndPente.Controls.Add("Forms.TextBox.1", "txtPenteFlLong")
    txtPenteFlLong.Left = 148: txtPenteFlLong.Top = 68
    txtPenteFlLong.Width = 38: txtPenteFlLong.Height = 16
    txtPenteFlLong.Enabled = False

    ' --- Cadre Etat ---------------------------------------------------------
    Dim fraEtat As MSForms.Frame
    Set fraEtat = Me.Controls.Add("Forms.Frame.1", "fraEtat")
    fraEtat.Caption = "Etat"
    fraEtat.Left = 6: fraEtat.Top = 486
    fraEtat.Width = 192: fraEtat.Height = 64

    Set lblP1 = CreerLabel(fraEtat, "lblP1", "P1 : -", 6, 12, 180)
    Set lblP2 = CreerLabel(fraEtat, "lblP2", "P2 : -", 6, 26, 180)
    Set lblSegment = CreerLabel(fraEtat, "lblSegment", "-", 6, 40, 180)

    ' --- Cadre Actions (disponible apres snap P2) ---------------------------
    Dim fraActions As MSForms.Frame
    Set fraActions = Me.Controls.Add("Forms.Frame.1", "fraActions")
    fraActions.Caption = "Actions"
    fraActions.Left = 6: fraActions.Top = 556
    fraActions.Width = 192: fraActions.Height = 72

    Set btnRetourInterp = fraActions.Controls.Add("Forms.CommandButton.1", "btnRetourInterp")
    btnRetourInterp.Caption = "Interpolation"
    btnRetourInterp.Left = 6: btnRetourInterp.Top = 14
    btnRetourInterp.Width = 86: btnRetourInterp.Height = 22
    btnRetourInterp.Enabled = False

    Set btnPlacerPente = fraActions.Controls.Add("Forms.CommandButton.1", "btnPlacerPente")
    btnPlacerPente.Caption = "Pente + fleche"
    btnPlacerPente.Left = 98: btnPlacerPente.Top = 14
    btnPlacerPente.Width = 88: btnPlacerPente.Height = 22
    btnPlacerPente.Enabled = False

    Set btnChemin = fraActions.Controls.Add("Forms.CommandButton.1", "btnChemin")
    btnChemin.Caption = "Chemin"
    btnChemin.Left = 6: btnChemin.Top = 38
    btnChemin.Width = 180: btnChemin.Height = 22
    btnChemin.Enabled = False
End Sub

'------------------------------------------------------------------------------
Private Function CreerLabel(oParent As MSForms.Frame, sNom As String, _
                            sCaption As String, dLeft As Double, dTop As Double, _
                            dWidth As Double) As MSForms.Label
    Set CreerLabel = oParent.Controls.Add("Forms.Label.1", sNom)
    CreerLabel.Caption = sCaption
    CreerLabel.Left = dLeft: CreerLabel.Top = dTop
    CreerLabel.Width = dWidth: CreerLabel.Height = 12
End Function

'==============================================================================
' Initialisation
'==============================================================================

'------------------------------------------------------------------------------
' Appele par InterpolationTopoV2 avant Show vbModeless.
Sub Initialiser(oSettings As CMstSettings)
    ConstruireControles   ' securite si Initialize n'a pas encore ete declenche
    Set m_oSettings = oSettings
    m_bInit = True

    ' Cercle : pre-remplir depuis les parametres
    txtDiametre.Text = Format$(m_oSettings.oCercle.Diametre, "0.00")
    txtCouleur.Text = CStr(m_oSettings.oCercle.Couleur)

    ' Niveaux : remplir les listes depuis le fichier DGN
    RemplirNiveaux cmbNiveau
    RemplirNiveaux cmbNiveauTexte

    ' Texte altitude : case + champs selon le mode
    chkTexteModele.Value = m_oSettings.oTexte.CommeModele
    txtCouleurTexte.Text = CStr(m_oSettings.oTexte.Couleur)
    txtDecimales.Text = CStr(m_oSettings.oTexte.Decimales)
    ActiverChampsTexte

    ' Indicateur pente
    chkPentePerso.Value = m_oSettings.oIndicPente.Perso
    txtPenteH.Text = Format$(m_oSettings.oIndicPente.Hauteur, "0.000")
    txtPenteL.Text = Format$(m_oSettings.oIndicPente.Largeur, "0.000")
    RemplirNiveaux cmbPenteNiveau
    txtPenteCoulTxt.Text = CStr(m_oSettings.oIndicPente.Couleur)
    txtPenteCoulFl.Text = CStr(m_oSettings.oIndicPente.FlecheCouleur)
    txtPenteFlLong.Text = Format$(m_oSettings.oIndicPente.FlecheLongueur, "0.00")
    txtPenteDec.Text = CStr(m_oSettings.oIndicPente.Decimales)
    ActiverChampsPente

    ' Pente decalage
    chkPente.Value = m_oSettings.oDecalage.PenteActive
    txtPente.Text = Format$(m_oSettings.oDecalage.Pente, "0.00")
    txtPente.Enabled = m_oSettings.oDecalage.PenteActive
    btnInverserPente.Enabled = m_oSettings.oDecalage.PenteActive

    ' Decalage fixe DZ
    chkDecalageFixe.Value = m_oSettings.oDecalage.DZActive
    txtDecalageDZ.Text = Format$(m_oSettings.oDecalage.DZ, "0.00")
    txtDecalageDZ.Enabled = m_oSettings.oDecalage.DZActive
    chkDecalIndPente.Value = m_oSettings.bDecalIndicPente

    ' Etat : reinitialiser
    ReinitialiserEtat

    m_bInit = False
End Sub

'------------------------------------------------------------------------------
Private Sub RemplirNiveaux(cmb As MSForms.ComboBox)
    cmb.Clear
    cmb.AddItem ""   ' premier element vide = niveau du texte P1
    Dim oLvl As Level
    For Each oLvl In ActiveDesignFile.Levels
        cmb.AddItem oLvl.Number & " : " & oLvl.Name
    Next
    cmb.ListIndex = 0  ' vide selectionne par defaut
End Sub

'------------------------------------------------------------------------------
Private Sub ActiverChampsPente()
    Dim bActif As Boolean
    bActif = m_oSettings.oIndicPente.Perso
    txtPenteH.Enabled = bActif
    txtPenteL.Enabled = bActif
    cmbPenteNiveau.Enabled = bActif
    txtPenteCoulTxt.Enabled = bActif
    txtPenteCoulFl.Enabled = bActif
    txtPenteFlLong.Enabled = bActif
End Sub

'------------------------------------------------------------------------------
Sub RafraichirPente()
    If m_oSettings Is Nothing Then Exit Sub
    m_bInit = True
    txtPenteH.Text = Format$(m_oSettings.oIndicPente.Hauteur, "0.000")
    txtPenteL.Text = Format$(m_oSettings.oIndicPente.Largeur, "0.000")
    txtPenteCoulTxt.Text = CStr(m_oSettings.oIndicPente.Couleur)
    m_bInit = False
End Sub

'------------------------------------------------------------------------------
' Active/desactive les champs du texte selon la case a cocher
Private Sub ActiverChampsTexte()
    Dim bLibre As Boolean
    bLibre = Not m_oSettings.oTexte.CommeModele
    txtCouleurTexte.Enabled = bLibre
    cmbNiveauTexte.Enabled = bLibre
End Sub

'------------------------------------------------------------------------------
' Appele par CSelectP1 apres la selection de P1 : en mode modele, affiche
' la couleur et le niveau herites du texte selectionne (champs grises).
Sub RafraichirTexte()
    If m_oSettings Is Nothing Then Exit Sub
    m_bInit = True
    txtCouleurTexte.Text = CStr(m_oSettings.oTexte.Couleur)
    cmbNiveauTexte.Text = m_oSettings.oTexte.NomNiveau
    txtDecimales.Text = CStr(m_oSettings.oTexte.Decimales)
    m_bInit = False
End Sub

'==============================================================================
' Mise a jour de l'etat par les classes de commande
'==============================================================================

Sub AfficherP1(oP As CPointRef)
    lblP1.Caption = "P1 : " & oP.Altitude
End Sub

Sub AfficherP2(oP As CPointRef)
    lblP2.Caption = "P2 : " & oP.Altitude
End Sub

Sub AfficherSegment(sInfo As String)
    lblSegment.Caption = sInfo
End Sub

Sub ReinitialiserEtat()
    lblP1.Caption = "P1 : -"
    lblP2.Caption = "P2 : -"
    lblSegment.Caption = "-"
    ActiverBoutonsActions False
End Sub

'------------------------------------------------------------------------------
' Active ou desactive les boutons Interpolation/Pente (disponibles apres snap P2).
Sub ActiverBoutonsActions(bActif As Boolean)
    btnRetourInterp.Enabled = bActif
    btnPlacerPente.Enabled = bActif
    btnChemin.Enabled = bActif
End Sub

'==============================================================================
' Evenements des controles : validation et ecriture dans m_oSettings
'
' Les controles etant crees au runtime, l'evenement Exit (extender) n'est pas
' disponible via WithEvents : la validation se fait sur Change. Une saisie
' invalide ou incomplete est simplement ignoree (les parametres gardent la
' derniere valeur valide) ; Entree reformate le champ depuis cette valeur.
'==============================================================================

Private Sub txtDiametre_Change()
    If m_bInit Then Exit Sub
    If m_oSettings Is Nothing Then Exit Sub
    Dim dDiam As Double
    dDiam = Val(Replace(Trim$(txtDiametre.Text), ",", "."))
    If dDiam > 0 Then m_oSettings.oCercle.Diametre = dDiam
End Sub

Private Sub txtDiametre_KeyDown(ByVal KeyCode As MSForms.ReturnInteger, _
                                ByVal Shift As Integer)
    If KeyCode = vbKeyReturn And Not m_oSettings Is Nothing Then _
        txtDiametre.Text = Format$(m_oSettings.oCercle.Diametre, "0.00")
End Sub

Private Sub txtCouleur_Change()
    If m_bInit Then Exit Sub
    If m_oSettings Is Nothing Then Exit Sub
    Dim sVal As String
    sVal = Trim$(txtCouleur.Text)
    If sVal = "" Then Exit Sub
    Dim nCoul As Long
    nCoul = CLng(Val(sVal))
    If nCoul >= 0 And nCoul <= 255 Then m_oSettings.oCercle.Couleur = nCoul
End Sub

Private Sub txtCouleur_KeyDown(ByVal KeyCode As MSForms.ReturnInteger, _
                               ByVal Shift As Integer)
    If KeyCode = vbKeyReturn And Not m_oSettings Is Nothing Then _
        txtCouleur.Text = CStr(m_oSettings.oCercle.Couleur)
End Sub

Private Sub cmbNiveau_Change()
    If m_bInit Then Exit Sub
    If m_oSettings Is Nothing Then Exit Sub
    m_oSettings.oCercle.NomNiveau = ExtraireNiveau(cmbNiveau.Text)
End Sub

'------------------------------------------------------------------------------
' Case a cocher : True = attributs du texte P1, False = choix libre
Private Sub chkTexteModele_Change()
    If m_bInit Then Exit Sub
    If m_oSettings Is Nothing Then Exit Sub
    m_oSettings.oTexte.CommeModele = (chkTexteModele.Value = True)
    ActiverChampsTexte
    ' Retour au mode modele : recharger les attributs du texte P1 si connu
    If m_oSettings.oTexte.CommeModele And m_oSettings.TextModeleDisponible Then
        m_oSettings.oTexte.ChargerDepuisElement m_oSettings.oTextModele
        RafraichirTexte
    End If
End Sub

Private Sub txtCouleurTexte_Change()
    If m_bInit Then Exit Sub
    If m_oSettings Is Nothing Then Exit Sub
    Dim sVal As String
    sVal = Trim$(txtCouleurTexte.Text)
    If sVal = "" Then Exit Sub
    Dim nCoul As Long
    nCoul = CLng(Val(sVal))
    If nCoul >= 0 And nCoul <= 255 Then m_oSettings.oTexte.Couleur = nCoul
End Sub

Private Sub txtCouleurTexte_KeyDown(ByVal KeyCode As MSForms.ReturnInteger, _
                                    ByVal Shift As Integer)
    If KeyCode = vbKeyReturn And Not m_oSettings Is Nothing Then _
        txtCouleurTexte.Text = CStr(m_oSettings.oTexte.Couleur)
End Sub

Private Sub cmbNiveauTexte_Change()
    If m_bInit Then Exit Sub
    If m_oSettings Is Nothing Then Exit Sub
    m_oSettings.oTexte.NomNiveau = ExtraireNiveau(cmbNiveauTexte.Text)
End Sub

Private Sub txtDecimales_Change()
    If m_bInit Then Exit Sub
    If m_oSettings Is Nothing Then Exit Sub
    Dim nDec As Integer
    nDec = CInt(Val(Trim$(txtDecimales.Text)))
    If nDec >= 0 And nDec <= 6 Then m_oSettings.oTexte.Decimales = nDec
End Sub

Private Sub txtDecimales_KeyDown(ByVal KeyCode As MSForms.ReturnInteger, _
                                  ByVal Shift As Integer)
    If KeyCode = vbKeyReturn And Not m_oSettings Is Nothing Then _
        txtDecimales.Text = CStr(m_oSettings.oTexte.Decimales)
End Sub

'------------------------------------------------------------------------------
' Extrait le niveau d'un item de combo "42 : Altimetrie" -> "42".
' ResolverNiveau (CMoteurGraphique) accepte nom ou numero ; vide = niveau P1.
Private Function ExtraireNiveau(ByVal sItem As String) As String
    sItem = Trim$(sItem)
    If InStr(sItem, " : ") > 0 Then
        ExtraireNiveau = Trim$(Left$(sItem, InStr(sItem, " : ") - 1))
    Else
        ExtraireNiveau = sItem
    End If
End Function

'==============================================================================
' Evenements Pente decalage
'==============================================================================

Private Sub chkPente_Change()
    If m_bInit Then Exit Sub
    If m_oSettings Is Nothing Then Exit Sub
    m_oSettings.oDecalage.PenteActive = (chkPente.Value = True)
    txtPente.Enabled = m_oSettings.oDecalage.PenteActive
    btnInverserPente.Enabled = m_oSettings.oDecalage.PenteActive
End Sub

Private Sub btnInverserPente_Click()
    If m_oSettings Is Nothing Then Exit Sub
    m_oSettings.oDecalage.Pente = -m_oSettings.oDecalage.Pente
    txtPente.Text = Format$(m_oSettings.oDecalage.Pente, "0.00")
End Sub

Private Sub txtPente_Change()
    If m_bInit Then Exit Sub
    If m_oSettings Is Nothing Then Exit Sub
    Dim dP As Double
    dP = Val(Replace(Trim$(txtPente.Text), ",", "."))
    m_oSettings.oDecalage.Pente = dP
End Sub

Private Sub txtPente_KeyDown(ByVal KeyCode As MSForms.ReturnInteger, _
                              ByVal Shift As Integer)
    If KeyCode = vbKeyReturn And Not m_oSettings Is Nothing Then _
        txtPente.Text = Format$(m_oSettings.oDecalage.Pente, "0.00")
End Sub

'==============================================================================
' Evenements Decalage fixe DZ
'==============================================================================

Private Sub chkDecalageFixe_Change()
    If m_bInit Then Exit Sub
    If m_oSettings Is Nothing Then Exit Sub
    m_oSettings.oDecalage.DZActive = (chkDecalageFixe.Value = True)
    txtDecalageDZ.Enabled = m_oSettings.oDecalage.DZActive
End Sub

Private Sub txtDecalageDZ_Change()
    If m_bInit Then Exit Sub
    If m_oSettings Is Nothing Then Exit Sub
    Dim dDZ As Double
    dDZ = Val(Replace(Trim$(txtDecalageDZ.Text), ",", "."))
    m_oSettings.oDecalage.DZ = dDZ
End Sub

Private Sub txtDecalageDZ_KeyDown(ByVal KeyCode As MSForms.ReturnInteger, _
                                   ByVal Shift As Integer)
    If KeyCode = vbKeyReturn And Not m_oSettings Is Nothing Then _
        txtDecalageDZ.Text = Format$(m_oSettings.oDecalage.DZ, "0.00")
End Sub

Private Sub chkDecalIndPente_Change()
    If m_bInit Then Exit Sub
    If m_oSettings Is Nothing Then Exit Sub
    m_oSettings.bDecalIndicPente = (chkDecalIndPente.Value = True)
End Sub

'==============================================================================
' Evenements Indicateur pente
'==============================================================================

Private Sub chkPentePerso_Change()
    If m_bInit Then Exit Sub
    If m_oSettings Is Nothing Then Exit Sub
    m_oSettings.oIndicPente.Perso = (chkPentePerso.Value = True)
    ActiverChampsPente
End Sub

Private Sub txtPenteH_Change()
    If m_bInit Then Exit Sub
    If m_oSettings Is Nothing Then Exit Sub
    Dim dVal As Double
    dVal = Val(Replace(Trim$(txtPenteH.Text), ",", "."))
    If dVal > 0 Then m_oSettings.oIndicPente.Hauteur = dVal
End Sub

Private Sub txtPenteH_KeyDown(ByVal KeyCode As MSForms.ReturnInteger, _
                               ByVal Shift As Integer)
    If KeyCode = vbKeyReturn And Not m_oSettings Is Nothing Then _
        txtPenteH.Text = Format$(m_oSettings.oIndicPente.Hauteur, "0.000")
End Sub

Private Sub txtPenteL_Change()
    If m_bInit Then Exit Sub
    If m_oSettings Is Nothing Then Exit Sub
    Dim dVal As Double
    dVal = Val(Replace(Trim$(txtPenteL.Text), ",", "."))
    If dVal > 0 Then m_oSettings.oIndicPente.Largeur = dVal
End Sub

Private Sub txtPenteL_KeyDown(ByVal KeyCode As MSForms.ReturnInteger, _
                               ByVal Shift As Integer)
    If KeyCode = vbKeyReturn And Not m_oSettings Is Nothing Then _
        txtPenteL.Text = Format$(m_oSettings.oIndicPente.Largeur, "0.000")
End Sub

Private Sub cmbPenteNiveau_Change()
    If m_bInit Then Exit Sub
    If m_oSettings Is Nothing Then Exit Sub
    m_oSettings.oIndicPente.NomNiveau = ExtraireNiveau(cmbPenteNiveau.Text)
End Sub

Private Sub txtPenteCoulTxt_Change()
    If m_bInit Then Exit Sub
    If m_oSettings Is Nothing Then Exit Sub
    Dim sVal As String: sVal = Trim$(txtPenteCoulTxt.Text)
    If sVal = "" Then Exit Sub
    Dim nCoul As Long: nCoul = CLng(Val(sVal))
    If nCoul >= 0 And nCoul <= 255 Then m_oSettings.oIndicPente.Couleur = nCoul
End Sub

Private Sub txtPenteCoulTxt_KeyDown(ByVal KeyCode As MSForms.ReturnInteger, _
                                     ByVal Shift As Integer)
    If KeyCode = vbKeyReturn And Not m_oSettings Is Nothing Then _
        txtPenteCoulTxt.Text = CStr(m_oSettings.oIndicPente.Couleur)
End Sub

Private Sub txtPenteCoulFl_Change()
    If m_bInit Then Exit Sub
    If m_oSettings Is Nothing Then Exit Sub
    Dim sVal As String: sVal = Trim$(txtPenteCoulFl.Text)
    If sVal = "" Then Exit Sub
    Dim nCoul As Long: nCoul = CLng(Val(sVal))
    If nCoul >= 0 And nCoul <= 255 Then m_oSettings.oIndicPente.FlecheCouleur = nCoul
End Sub

Private Sub txtPenteCoulFl_KeyDown(ByVal KeyCode As MSForms.ReturnInteger, _
                                    ByVal Shift As Integer)
    If KeyCode = vbKeyReturn And Not m_oSettings Is Nothing Then _
        txtPenteCoulFl.Text = CStr(m_oSettings.oIndicPente.FlecheCouleur)
End Sub

Private Sub txtPenteFlLong_Change()
    If m_bInit Then Exit Sub
    If m_oSettings Is Nothing Then Exit Sub
    Dim dVal As Double
    dVal = Val(Replace(Trim$(txtPenteFlLong.Text), ",", "."))
    If dVal > 0 Then m_oSettings.oIndicPente.FlecheLongueur = dVal
End Sub

Private Sub txtPenteFlLong_KeyDown(ByVal KeyCode As MSForms.ReturnInteger, _
                                    ByVal Shift As Integer)
    If KeyCode = vbKeyReturn And Not m_oSettings Is Nothing Then _
        txtPenteFlLong.Text = Format$(m_oSettings.oIndicPente.FlecheLongueur, "0.00")
End Sub

Private Sub txtPenteDec_Change()
    If m_bInit Then Exit Sub
    If m_oSettings Is Nothing Then Exit Sub
    Dim nDec As Integer
    nDec = CInt(Val(Trim$(txtPenteDec.Text)))
    If nDec >= 0 And nDec <= 6 Then m_oSettings.oIndicPente.Decimales = nDec
End Sub

Private Sub txtPenteDec_KeyDown(ByVal KeyCode As MSForms.ReturnInteger, _
                                 ByVal Shift As Integer)
    If KeyCode = vbKeyReturn And Not m_oSettings Is Nothing Then _
        txtPenteDec.Text = CStr(m_oSettings.oIndicPente.Decimales)
End Sub

'==============================================================================
' Boutons Actions (apres snap P2)
'==============================================================================

Private Sub btnPlacerPente_Click()
    CommandState.StartPrimitive New CPlacerPente
End Sub

Private Sub btnRetourInterp_Click()
    CommandState.StartPrimitive New CPlacerPoint
End Sub

Private Sub btnChemin_Click()
    CommandState.StartPrimitive New CPlacerChemin
End Sub

'==============================================================================
' Fermeture
'==============================================================================

'------------------------------------------------------------------------------
' Croix de la fenetre : terminer la commande SANS decharger le formulaire.
' Les classes de commande referencent l'instance par defaut : la decharger
' ici en recreerait une vierge (m_oSettings = Nothing) au prochain acces.
Private Sub UserForm_QueryClose(Cancel As Integer, CloseMode As Integer)
    If CloseMode = vbFormControlMenu Then
        Cancel = 1
        Me.Hide
        CommandState.StartDefaultCommand
    End If
End Sub

Attribute VB_Name = "frmReseauEP"
Attribute VB_Base = "0{827E1E53-79F0-4956-8E95-3C5B7627FF44}{3806E481-FFB8-4F15-AAA5-62F3ED1BE1CA}"
Attribute VB_GlobalNameSpace = False
Attribute VB_Creatable = False
Attribute VB_PredeclaredId = True
Attribute VB_Exposed = False
Attribute VB_TemplateDerived = False
Attribute VB_Customizable = False

'==============================================================================
' frmReseauEP - Tool Settings de la commande Pente Reseau EU/EP
'
' Cadres :
'   Etat        : lecture P1 et P2 (Fe / T / Prof), distance 2D, pente
'   Recherche   : rayon de recherche autour du clic (u.m.)
'   Indicateur  : parametres perso hauteur/couleur du texte pente et de la fleche,
'                 independants des reglages Interpolation V2
'
' Tous les controles sont crees au runtime dans ConstruireControles (le .frx
' n'est qu'un blob de formulaire vide, cf. CLAUDE.md).
'==============================================================================
Option Explicit

Private m_oSettings  As CMstSettings
Private m_bInit      As Boolean
Private m_bConstruit As Boolean

' --- Etat ---
Private lblP1        As MSForms.Label
Private lblP2        As MSForms.Label
Private lblDist      As MSForms.Label
Private lblPente     As MSForms.Label

' --- Recherche ---
Private WithEvents txtTol As MSForms.TextBox
Attribute txtTol.VB_VarHelpID = -1

' --- Indicateur pente ---
Private WithEvents chkPerso As MSForms.CheckBox
Attribute chkPerso.VB_VarHelpID = -1
Private WithEvents txtHauteur As MSForms.TextBox
Attribute txtHauteur.VB_VarHelpID = -1
Private WithEvents txtCoulTxt As MSForms.TextBox
Attribute txtCoulTxt.VB_VarHelpID = -1
Private WithEvents txtLongFleche As MSForms.TextBox
Attribute txtLongFleche.VB_VarHelpID = -1
Private WithEvents txtCoulFleche As MSForms.TextBox
Attribute txtCoulFleche.VB_VarHelpID = -1

'==============================================================================
' Construction des controles
'==============================================================================

Private Sub UserForm_Initialize()
    ConstruireControles
End Sub

Private Sub ConstruireControles()
    If m_bConstruit Then Exit Sub
    m_bConstruit = True

    Me.Caption = "Pente Reseau EU/EP"
    Me.Width = 212
    Me.Height = 340

    Dim dY As Double
    dY = 6

    ' --- Cadre Etat -----------------------------------------------------------
    Dim fraEtat As MSForms.Frame
    Set fraEtat = Me.Controls.Add("Forms.Frame.1", "fraEtat")
    fraEtat.Caption = "Etat"
    fraEtat.Left = 6: fraEtat.Top = dY
    fraEtat.Width = 192: fraEtat.Height = 68

    Set lblP1 = CreerLabel(fraEtat, "lblP1", "P1 : -", 6, 12, 180)
    Set lblP2 = CreerLabel(fraEtat, "lblP2", "P2 : -", 6, 24, 180)
    Set lblDist = CreerLabel(fraEtat, "lblDist", "Distance : -", 6, 38, 180)
    Set lblPente = CreerLabel(fraEtat, "lblPente", "Pente : -", 6, 50, 180)

    dY = dY + 74

    ' --- Cadre Recherche ------------------------------------------------------
    Dim fraRech As MSForms.Frame
    Set fraRech = Me.Controls.Add("Forms.Frame.1", "fraRech")
    fraRech.Caption = "Recherche"
    fraRech.Left = 6: fraRech.Top = dY
    fraRech.Width = 192: fraRech.Height = 38

    CreerLabel fraRech, "lblTol", "Rayon (u.m.) :", 6, 14, 70
    Set txtTol = fraRech.Controls.Add("Forms.TextBox.1", "txtTol")
    txtTol.Left = 82: txtTol.Top = 12
    txtTol.Width = 48: txtTol.Height = 16
    txtTol.Text = "5.00"

    dY = dY + 44

    ' --- Cadre Indicateur pente ----------------------------------------------
    Dim fraInd As MSForms.Frame
    Set fraInd = Me.Controls.Add("Forms.Frame.1", "fraInd")
    fraInd.Caption = "Indicateur pente (texte + fleche)"
    fraInd.Left = 6: fraInd.Top = dY
    fraInd.Width = 192: fraInd.Height = 130

    Set chkPerso = fraInd.Controls.Add("Forms.CheckBox.1", "chkPerso")
    chkPerso.Caption = "Reglages personnalises"
    chkPerso.Left = 6: chkPerso.Top = 10
    chkPerso.Width = 180: chkPerso.Height = 14
    chkPerso.Value = True

    CreerLabel fraInd, "lblHt", "Hauteur texte :", 6, 32, 78
    Set txtHauteur = fraInd.Controls.Add("Forms.TextBox.1", "txtHauteur")
    txtHauteur.Left = 108: txtHauteur.Top = 30
    txtHauteur.Width = 48: txtHauteur.Height = 16

    CreerLabel fraInd, "lblCTxt", "Couleur texte :", 6, 52, 78
    Set txtCoulTxt = fraInd.Controls.Add("Forms.TextBox.1", "txtCoulTxt")
    txtCoulTxt.Left = 108: txtCoulTxt.Top = 50
    txtCoulTxt.Width = 30: txtCoulTxt.Height = 16

    CreerLabel fraInd, "lblLF", "Longueur fleche :", 6, 72, 90
    Set txtLongFleche = fraInd.Controls.Add("Forms.TextBox.1", "txtLongFleche")
    txtLongFleche.Left = 108: txtLongFleche.Top = 70
    txtLongFleche.Width = 48: txtLongFleche.Height = 16

    CreerLabel fraInd, "lblCF", "Couleur fleche :", 6, 92, 90
    Set txtCoulFleche = fraInd.Controls.Add("Forms.TextBox.1", "txtCoulFleche")
    txtCoulFleche.Left = 108: txtCoulFleche.Top = 90
    txtCoulFleche.Width = 30: txtCoulFleche.Height = 16

    CreerLabel fraInd, "lblAide", "(decoche = defauts V2)", 6, 112, 180
End Sub

'------------------------------------------------------------------------------
Private Function CreerLabel(oParent As MSForms.Frame, sNom As String, _
                            sCaption As String, dLeft As Double, dTop As Double, _
                            dWidth As Double) As MSForms.Label
    Set CreerLabel = oParent.Controls.Add("Forms.Label.1", sNom)
    CreerLabel.Caption = sCaption
    CreerLabel.Left = dLeft: CreerLabel.Top = dTop
    CreerLabel.Width = dWidth: CreerLabel.Height = 12
End Function

'==============================================================================
' Initialisation
'==============================================================================

Sub Initialiser(oSettings As CMstSettings)
    ConstruireControles
    Set m_oSettings = oSettings
    m_bInit = True

    ' Par defaut, on active les reglages perso (sinon la V2 n'ayant pas de
    ' texte-modele P1, les tailles heritees restent a la valeur par defaut 0.1).
    m_oSettings.oIndicPente.Perso = (chkPerso.Value = True)

    txtTol.Text = Format$(g_dTolReseau, "0.00")
    txtHauteur.Text = Format$(m_oSettings.oIndicPente.Hauteur, "0.000")
    txtCoulTxt.Text = CStr(m_oSettings.oIndicPente.Couleur)
    txtLongFleche.Text = Format$(m_oSettings.oIndicPente.FlecheLongueur, "0.00")
    txtCoulFleche.Text = CStr(m_oSettings.oIndicPente.FlecheCouleur)

    ActiverChampsPerso
    ReinitialiserEtat

    m_bInit = False
End Sub

Private Sub ActiverChampsPerso()
    Dim b As Boolean
    b = (chkPerso.Value = True)
    txtHauteur.Enabled = b
    txtCoulTxt.Enabled = b
    txtLongFleche.Enabled = b
    txtCoulFleche.Enabled = b
End Sub

'==============================================================================
' Mise a jour depuis les classes de commande
'==============================================================================

Sub AfficherBoiteP1(oInfo As CBoiteEPInfo)
    lblP1.Caption = "P1 : " & DecrireBoite(oInfo)
End Sub

Sub AfficherBoiteP2(oInfo As CBoiteEPInfo)
    lblP2.Caption = "P2 : " & DecrireBoite(oInfo)
End Sub

Sub AfficherDistancePente(dDist As Double, dPente As Double)
    lblDist.Caption = "Distance : " & Format$(dDist, "0.00") & " u.m."
    lblPente.Caption = "Pente : " & Format$(dPente, "0.0") & " %"
End Sub

Sub ReinitialiserEtat()
    lblP1.Caption = "P1 : -"
    lblP2.Caption = "P2 : -"
    lblDist.Caption = "Distance : -"
    lblPente.Caption = "Pente : -"
End Sub

' Efface seulement les infos de P2 (pente + distance), pour l'auto-chainage
' apres placement pente (P2 devient P1 et on repart snap P2).
Sub EffacerP2()
    lblP2.Caption = "P2 : -"
    lblDist.Caption = "Distance : -"
    lblPente.Caption = "Pente : -"
End Sub

'==============================================================================
' Evenements Recherche
'==============================================================================

Private Sub txtTol_Change()
    If m_bInit Then Exit Sub
    Dim d As Double
    d = Val(Replace(Trim$(txtTol.Text), ",", "."))
    If d > 0 Then g_dTolReseau = d
End Sub

Private Sub txtTol_KeyDown(ByVal KeyCode As MSForms.ReturnInteger, _
                            ByVal Shift As Integer)
    If KeyCode = vbKeyReturn Then _
        txtTol.Text = Format$(g_dTolReseau, "0.00")
End Sub

'==============================================================================
' Evenements Indicateur pente
'==============================================================================

Private Sub chkPerso_Change()
    If m_bInit Then Exit Sub
    If m_oSettings Is Nothing Then Exit Sub
    m_oSettings.oIndicPente.Perso = (chkPerso.Value = True)
    ActiverChampsPerso
End Sub

Private Sub txtHauteur_Change()
    If m_bInit Then Exit Sub
    If m_oSettings Is Nothing Then Exit Sub
    Dim d As Double
    d = Val(Replace(Trim$(txtHauteur.Text), ",", "."))
    If d > 0 Then
        m_oSettings.oIndicPente.Hauteur = d
        m_oSettings.oIndicPente.Largeur = d
    End If
End Sub

Private Sub txtCoulTxt_Change()
    If m_bInit Then Exit Sub
    If m_oSettings Is Nothing Then Exit Sub
    Dim sVal As String: sVal = Trim$(txtCoulTxt.Text)
    If sVal = "" Then Exit Sub
    Dim n As Long: n = CLng(Val(sVal))
    If n >= 0 And n <= 255 Then m_oSettings.oIndicPente.Couleur = n
End Sub

Private Sub txtLongFleche_Change()
    If m_bInit Then Exit Sub
    If m_oSettings Is Nothing Then Exit Sub
    Dim d As Double
    d = Val(Replace(Trim$(txtLongFleche.Text), ",", "."))
    If d > 0 Then m_oSettings.oIndicPente.FlecheLongueur = d
End Sub

Private Sub txtCoulFleche_Change()
    If m_bInit Then Exit Sub
    If m_oSettings Is Nothing Then Exit Sub
    Dim sVal As String: sVal = Trim$(txtCoulFleche.Text)
    If sVal = "" Then Exit Sub
    Dim n As Long: n = CLng(Val(sVal))
    If n >= 0 And n <= 255 Then m_oSettings.oIndicPente.FlecheCouleur = n
End Sub

'==============================================================================
' Fermeture par la croix : quitter la commande
'==============================================================================

Private Sub UserForm_QueryClose(Cancel As Integer, CloseMode As Integer)
    If CloseMode = vbFormControlMenu Then
        Cancel = 1
        Me.Hide
        CommandState.StartDefaultCommand
    End If
End Sub
